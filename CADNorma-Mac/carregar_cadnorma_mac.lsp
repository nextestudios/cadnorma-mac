; CADNorma Mac 2027 - carregamento manual, UTF-8.
(if (= 0 (getvar "LISPSYS"))
  (progn (alert "Defina LISPSYS=1, reinicie o AutoCAD e recarregue. Este pacote usa UTF-8.") (exit)))
(setq cnp_mac_file (getfiled "Selecione ESTE carregar_cadnorma_mac.lsp na copia adaptada" "" "lsp" 0))
(if (not cnp_mac_file) (exit))
(setq cnp_root (vl-filename-directory cnp_mac_file) cnp_netroot cnp_root)
(if (not (findfile (strcat cnp_root "/lisp/mac-port.lsp")))
  (progn (alert "Esta pasta nao e a copia adaptada completa.") (exit)))
(setq cnp_user "cnus" cnp_predef_messag "\nCADNorma Mac - adaptacao experimental parcial.\n")
(load (strcat cnp_root "/lisp/mac-port.lsp"))
(copy_shape)
(setq cnp_mac_old_echo (getvar "CMDECHO"))
(load (strcat cnp_root "/lisp/cadnorma.lsp"))
(setvar "CMDECHO" cnp_mac_old_echo)
(load (strcat cnp_root "/lisp/lib_mac.lsp"))
(princ cnp_predef_messag)
(princ "CFG configura o desenho; GERENTE lista os comandos. Atalhos: CNMACATALHOS.\n")
(princ "A carga define INSUNITS=4 como no original. Use primeiro um desenho descartavel.\n")
(princ "Os comandos de fabricantes sao carregados sob demanda a partir dos fontes LSP.\n")

(defun c:acqualife () (load (strcat cnp_root "/fabricantes/acqualife.lsp")) (princ))
(defun c:eternit () (load (strcat cnp_root "/fabricantes/eternit.lsp")) (princ))
(defun c:fibratec () (load (strcat cnp_root "/fabricantes/fibratec.lsp")) (princ))
(defun c:gravia () (load (strcat cnp_root "/fabricantes/gravia.lsp")) (princ))
(defun c:igui () (load (strcat cnp_root "/fabricantes/igui.lsp")) (princ))
(defun c:jacuzzi () (load (strcat cnp_root "/fabricantes/jacuzzi.lsp")) (princ))
(defun c:termotec () (load (strcat cnp_root "/fabricantes/termotec.lsp")) (princ))
(c:cnmacstatus)
(princ)
