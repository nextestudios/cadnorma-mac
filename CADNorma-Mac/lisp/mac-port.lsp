; Backups persistentes: nao usar vl-filename-mktemp, cujos nomes sao removidos ao sair.
(defun cnp:backup-name (/ stem index candidate)
  (setq stem (strcat cnp_root "/cadnorma-backup-" (rtos (getvar "CDATE") 2 8) "-") index 1)
  (setq candidate (strcat stem (itoa index) ".bak"))
  (while (findfile candidate)
    (setq index (1+ index) candidate (strcat stem (itoa index) ".bak")))
  candidate
)
; CADNorma Mac experimental. Nenhuma chamada a COM ou shell.
(defun cnp:unsupported (name)
  (alert (strcat "CADNorma Mac: indisponivel nesta versao: " name "\nDepende de menus Windows ou de SLIDELIB.EXE. Nenhuma alteracao foi iniciada."))
  (exit)
)
(defun cnp:copy-overwrite (src dst / old)
  (if (not (findfile src)) (progn (alert (strcat "Origem ausente: " src)) (exit)))
  (setq old nil)
  (if (findfile dst)
    (progn
      (setq old (cnp:backup-name))
      (if (not (vl-file-rename dst old)) (progn (alert (strcat "Falha ao preservar: " dst)) (exit)))
    )
  )
  (if (null (vl-file-copy src dst))
    (progn
      (if (findfile dst) (vl-file-delete dst))
      (if old (vl-file-rename old dst))
      (alert (strcat "Falha ao copiar: " src "\npara: " dst))
      (exit)
    )
  )
  (if old (prompt (strcat "\nVersao anterior preservada: " old)))
  T
)
(defun cnp:copy-dir (src dst / names n count)
  (if (not (vl-file-directory-p dst))
    (if (not (vl-mkdir dst)) (progn (alert (strcat "Falha ao criar: " dst)) (exit))))
  (setq names (vl-directory-files src nil 1) count 0)
  (if (not names) (progn (alert (strcat "Diretorio vazio ou inacessivel: " src)) (exit)))
  (foreach n names
    (cnp:copy-overwrite (strcat src "/" n) (strcat dst "/" n))
    (setq count (1+ count)))
  (prompt (strcat "\nArquivos copiados: " (itoa count)))
  (princ)
)
(defun cnp:edit-shortcuts ()
  (alert (strcat "Edite este arquivo no TextEdit em modo texto simples (UTF-8):\n" cnp_root "/lisp/teclado.lsp\nDepois execute CNMACATALHOS. Ao salvar, preserve a extensao .lsp."))
)
(defun c:cnmacatalhos () (load (strcat cnp_root "/lisp/teclado.lsp")) (princ))
(defun copy_shape (/ n missing)
  (setq missing nil)
  (foreach n '("interrup.shx" "perigo.shx" "cercaeletr.shx" "seta1.shx" "seta2.shx")
    (if (not (findfile n)) (setq missing (cons n missing))))
  (if missing
    (progn
      (alert (strcat "Adicione aos Support File Search Paths:\n" cnp_root "/modelos\n" cnp_root "/hatch\nRecursos SHX nao localizados. Veja INSTALACAO-E-TESTES.txt."))
      (exit)))
  T
)
(defun c:cnmacstatus ()
  (prompt (strcat "\nCADNorma Mac experimental, raiz: " cnp_root "\nPortabilidade parcial; consulte RELATORIO.html e MATRIZ-FUNCOES.csv.\nCarga e smoke test aprovados; validacao funcional parcial. LIB indisponivel: slide_image nao suportado. Veja RESULTADO-TESTES.txt.\nGERENTE abre a lista de comandos; CFG configura o desenho."))
  (princ)
)
(defun c:gerente (/ id result pick)
  (setq id (load_dialog (strcat cnp_root "/lisp/cnmac.dcl")))
  (if (< id 0) (progn (alert "Falha ao abrir cnmac.dcl") (exit)))
  (if (not (new_dialog "cnmac" id)) (progn (unload_dialog id) (exit)))
  (start_list "comandos") (mapcar 'add_list cnp_mac_commands) (end_list)
  (setq pick 0)
  (set_tile "comandos" "0")
  (action_tile "comandos" "(setq pick (atoi $value))")
  (action_tile "accept" "(done_dialog 1)")
  (action_tile "cancel" "(done_dialog 0)")
  (setq result (start_dialog))
  (unload_dialog id)
  (if (= result 1) (eval (list (read (strcat "c:" (nth pick cnp_mac_commands))))))
  (princ)
)

(setq cnp_mac_commands '("01" "02" "03" "04" "05" "06" "07" "08" "2" "?CFG" "ALDIM" "ALLAY" "ALTEXT" "APO" "ARL" "ATANG" "ATCOL" "ATEXP" "ATXH" "AZM" "B1" "B2" "BIB" "BKC" "BKR" "BKS" "BLKD" "BLKR" "BLKS" "BY" "C0" "C1" "C2" "C3" "C4" "C5" "C6" "C7" "CAT" "CB1" "CB2" "CB3" "CB4" "CB5" "CB6" "CBOX" "CBT" "CFG" "CHA" "CHC" "CHD" "CHL" "CHQ" "CN_ABOUT" "COB" "CPC" "CPE" "CPED" "CR" "CRT1" "CRT2" "CSC" "CUR" "CURVAS" "CVE" "CVN" "CXA" "CXB" "D2P" "DATA" "DB" "DC" "DC2" "DCE" "DCE2" "DD" "DD2" "DECL" "DESCOL" "DG" "DG2" "DIATUB" "DIVI" "DL" "DL1" "DL2" "DLD" "DLD2" "DN" "DN1" "DN2" "DR" "DR2" "DSNV" "DTE" "DTX" "DU" "DULXEXTD" "DULXTRIM" "DWG" "EA_FATOR" "EIXP" "ELDV" "EL_FATOR" "EQCOLOR" "ESC" "ESPEC" "ETS" "EX1" "EX2" "EX3" "F0" "FIO" "FIO2" "FZ" "FZE" "FZV" "GERENTE" "GRC" "GRE" "GRF" "GRG" "GRP" "GRX" "GV1" "GV2" "ID1" "ID10" "ID11" "ID12" "ID13" "ID14" "ID15" "ID16" "ID17" "ID18" "ID19" "ID2" "ID20" "ID3" "ID4" "ID5" "ID6" "ID7" "ID8" "ID9" "IDCOL" "IDJ" "IDP" "IDTUB" "IEDIM" "INCL" "IP2" "IP3" "ISF" "ISK" "ISO" "IT1" "ITN" "JN" "K1" "K2" "K3" "LAC" "LALT" "LAY" "LCCL" "LCEL" "LCNT" "LCPC" "LCRC" "LDOT" "LDSD" "LDVD" "LEG" "LESTE" "LHD1" "LHD2" "LIB" "LIM" "LINC" "LINEMEND" "LINS" "LINT" "LKL" "LPHT" "LPRG" "LPRR" "LRC1" "LRC2" "LST1" "LST2" "LST3" "LTER" "LTRL" "M2" "M2P" "MALHA" "MOS" "MR" "MULT" "NE" "NET_BLKD" "NET_GRP" "NET_RU" "NE_DEC" "NOG" "NORTE" "NV" "NVC1" "NVC2" "NVP" "OFE" "OFL" "ONE" "ONL" "OSS" "P1" "P2" "P3" "P4" "P5" "P6" "P7" "P8" "PBOX" "PFR" "PKA" "PKL" "PLAREA" "PLWID" "PRESUFIX" "PRF" "PT" "PT2" "PT3" "PTX" "PUB" "QBAK" "QD" "QD2" "QEXP" "QID" "QIMP" "QL" "QL2" "QN" "QRST" "QS1" "QS2" "QTAB" "R100" "R120" "R140" "R175" "R200" "R50" "R60" "R70" "R80" "R90" "RSCALE" "RTX" "RU" "RV1" "RV2" "SC1" "SC2" "SC3" "SCC" "SCD" "SCDIM" "SCG" "SET" "SOBE" "SOMA" "SOMAREA" "SPLDV" "SPLIT" "SPLMU" "SQ1" "SQ2" "SSA" "SSN" "ST1" "ST2" "STC" "SUBAREA" "SUBT" "T1" "T2" "T3" "T4" "T5" "T6" "T7" "TALUDE" "TA_FATOR" "TBOX" "TCR" "TCT" "TISO" "TIT" "TOCOLOR" "TPT" "TP_LOC_NE" "TP_LOC_SEC" "TP_LOC_TNE" "TP_LOC_TOPOG" "TRCOLOR" "TROT" "TT1" "TT10" "TT11" "TT12" "TT13" "TT14" "TT15" "TT16" "TT17" "TT18" "TT19" "TT2" "TT20" "TT3" "TT4" "TT5" "TT6" "TT7" "TT8" "TT9" "TWE" "TWL" "TWV" "TXA" "TXAREA" "TXD" "TXDIST" "TXSEQ" "UB" "ULK" "ULKA" "ULTAREA" "UM" "USA" "USU" "V2" "VFZ" "VISO" "VP_LOCK" "VP_UNLOCK" "VP_XP" "VSC" "VUF" "VWP" "XTE" "XTRIM"))

(defun cnp:require-vars (names / n)
  (foreach n names
    (if (null (getvar n))
      (progn (alert (strcat "Variavel requerida nao disponivel: " n "\nConfiguracao interrompida antes de modificar o desenho. Veja o relatorio.")) (exit))))
  T
)
