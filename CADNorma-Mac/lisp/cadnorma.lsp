; Extensao COM Windows removida apos auditoria de chamadas.
;************************************************************
;Cadnorma Professional
;por Denio Guimarães
;Niterói, RJ
;versão 1.5 (nov/2011)
;************************************************************

;função que abre a toolbar principal
; c:gerente definido no adaptador mac-port.lsp
(defun c:ub () (command "._undo" "_b"))
(defun c:um () (command "._undo" "_m"))


;funções para salvar e resgatar os osnaps preferidos

;salva o osnap atual
(defun c:oss ()
  (setq myosnap (getvar "osmode"))
  (setq open_file (open (strcat cnp_root "/config/myosnap.txt") "w" "utf8"))
  (write-line (rtos (getvar "osmode") 2 0) open_file)
  (close open_file)
  (princ)
)

;resgata o osnap do usuário
(if (not (findfile (strcat cnp_root "/config/myosnap.txt")))
  (progn
    (setq open_file (open (strcat cnp_root "/config/myosnap.txt") "w" "utf8"))
    (write-line "255" open_file)
    (close open_file)
    (setvar "osmode" 255)
  )
  (progn
    (setq open_file (open (strcat cnp_root "/config/myosnap.txt") "r" "utf8"))
    (setq myosnap (fix (distof (read-line open_file))))
    (close open_file)
  )
)

;função que descarrega o Cadnorma
(defun c:cn_unload () (cnp:unsupported "c:cn_unload"))


;******************************************************************************
;******************************************************************************
;definições iniciais
;******************************************************************************
;******************************************************************************
(setvar "cmdecho" 0)
(setvar "insunits" 4)
(setq scdim_newscale 1.0)

;definição das primeiras variáveis globais
(setq
    ;reais
    cn7_msscl 	(getvar "userr3")
    cn7_dimunit (getvar "userr4")
    cn7_dwgunit (getvar "userr5")
    cn7_dzin 	(getvar "dimzin")
)

;textos - controle de layers
(cond
  ((= 0 (getvar "useri5")) (setq cdn_txt 1 cus_txt 1))
  ((= 1 (getvar "useri5")) (setq cdn_txt 1 cus_txt 0))
  ((= 2 (getvar "useri5")) (setq cdn_txt 0 cus_txt 1))
  ((= 3 (getvar "useri5")) (setq cdn_txt 0 cus_txt 0))
)

;dim - controle de layers
(cond
  ((= 0 (getvar "useri4")) (setq cdn_dim 1 cus_dim 1))
  ((= 1 (getvar "useri4")) (setq cdn_dim 1 cus_dim 0))
  ((= 2 (getvar "useri4")) (setq cdn_dim 0 cus_dim 1))
  ((= 3 (getvar "useri4")) (setq cdn_dim 0 cus_dim 0))
)

;alturas dos textos regulares
(setq hf_r50 1.25 hf_r60 1.5 hf_r70 1.75 hf_r80 2.0 hf_90 2.25
	hf_r100 2.5 hf_r120 3.0 hf_r140 3.5 hf_r175 4.375
	hf_r200 5.0 )

;zerando contadores
(setq cont-k1 0 cont-k2 0 cont-k3 0  cont-kk 0)


;coleção de escalas regulares
(defun reg_scale ()
  (if (not (findfile (strcat cnp_root "/config/reg_scale.txt")))
    (progn
      (setq reg_scale_list
	 (list
	   "1" "10" "100" "1000" "10000" "100000" "1000000"
	   "12.5" "125" "1250" "12500" "125000"
	   "1.5" "15" "150" "1500" "15000" "150000"
	   "2" "20" "200" "2000" "20000" "200000"
	   "2.500" "25" "250" "2500" "25000" "250000"
	   "3" "30" "300" "3000" "30000" "300000"
	   "4" "40" "400" "4000" "40000" "400000"
	   "5" "50" "500" "5000" "50000" "500000"
	   "7.500" "75" "750" "7500" "75000" "750000"
	 )
      )
      (setq open_file (open (strcat cnp_root "/config/reg_scale.txt") "w" "utf8"))
      (foreach n reg_scale_list
	(write-line n open_file)
      )
      (close open_file)
    )
    (progn
      (setq reg_scale_list (list " "))
      (setq open_file (open (strcat cnp_root "/config/reg_scale.txt") "r" "utf8"))
      (while (/= nil (setq linha (read-line open_file)))
	(setq reg_scale_list (append reg_scale_list (list linha)))
      )
      (close open_file)
      (setq reg_scale_list (cdr reg_scale_list))
    )
  )
)

;cria lista d escalas regulares
(reg_scale)


;******************************************************************************
;Controle de Escalas Regulares                                                
;******************************************************************************

;altera a coleção d escalas regulares
(defun c:rscale ()
  (setq rscale_nova nil rscale_list_n nil)
  (reg_scale)
  (cn7_rscale)
  (princ)
)

;abre e gerencia DCL
(defun cn7_rscale ()
  (setq dcl_id (load_dialog (strcat cnp_root "/lisp/cadnorma.dcl")))
  (if (not (new_dialog "cn7_regscale" dcl_id)) (exit))
  (start_list "cn7_rscale_list")
  (mapcar 'add_list reg_scale_list)
  (end_list)
  (action_tile "cn7_rscale_list" "(setq rscale_list_n $value)")
  (action_tile "cancel" "(done_dialog 0)")
  (action_tile "accept" "(done_dialog 1)")
  (action_tile "cn7_rscale_add" "(done_dialog 2)")
  (action_tile "cn7_rscale_remove" "(done_dialog 3)")
  (action_tile "cn7_rscale_reset" "(done_dialog 4)")
  (setq rscale_dialog (start_dialog))
  (unload_dialog dcl_id)
  (if (= 1 rscale_dialog) (rscale_ok))
  (if (= 2 rscale_dialog) (rscale_add))
  (if (= 3 rscale_dialog) (rscale_remove))
  (if (= 4 rscale_dialog) (rscale_reset))
)

;Função OK
(defun rscale_ok ()
  (setq open_file (open (strcat cnp_root "/config/reg_scale.txt") "w" "utf8"))
      (foreach n reg_scale_list
	(write-line n open_file)
      )
      (close open_file)
)

;função Adicionar
(defun rscale_add ()
  (setq dcl_id (load_dialog (strcat cnp_root "/lisp/cadnorma.dcl")))
  (if (not (new_dialog "cn7_regscale_add" dcl_id)) (exit))
  (mode_tile "rscale_newscale" 2)
  (action_tile "rscale_newscale" "(setq rscale_nova $value)")
  (action_tile "cancel" "(done_dialog 0)")
  (action_tile "accept" "(done_dialog 1)")
  (setq rscale_add_dialog (start_dialog))
  (unload_dialog dcl_id)
  (if (= 1 rscale_add_dialog) (rscale_add_ok))
)

;adiciona nova escala à lista
(defun rscale_add_ok ()
  (if (and (/= nil rscale_nova) (/= "" rscale_nova) (distof rscale_nova))
    (progn
      (setq reg_scale_list (acad_strlsort (append reg_scale_list (list rscale_nova))))
      (setq open_file (open (strcat cnp_root "/config/reg_scale.txt") "w" "utf8"))
      (foreach n reg_scale_list
	(write-line n open_file)
      )
      (close open_file)
      (cn7_rscale)
    )
    (progn
      (alert "Valor Inválido\nTente novamente")
      (rscale_add)
    )
  )
)

  
;remove uma escala da lista
(defun rscale_remove ()
  (if (= nil rscale_list_n)
    (progn
      (alert "Nenhuma Escala Selecionada\npara Remoção!\nTente Novamente...")
      (cn7_rscale)
    )
    (progn
      (setq counter 0 rscale_rem (fix (distof rscale_list_n))
	    rscale_len (length reg_scale_list) rscale_newlist (list ""))
      (repeat rscale_len
	(if (/= counter rscale_rem)
	  (setq rscale_newlist (append rscale_newlist (list (nth counter reg_scale_list))))
	)
	(setq counter (1+ counter))
      )
      (setq rscale_newlist (cdr rscale_newlist))
    )
  )
  (setq reg_scale_list rscale_newlist)
  (setq rscale_list_n nil)
  (cn7_rscale)
)

;Função RESET
(defun rscale_reset ()
  (cn7_alert_ok_cancel
    "Deseja realmente restaurar"
    "as escalas originais do Cadnorma?"
    "(Escalas adicionadas serão perdidas!)"
  )
  (if (= alert_resp "ok")
    (progn
      (setq reg_scale_list
	 (list
	   "1" "10" "100" "1000" "10000" "100000" "1000000"
	   "12.5" "125" "1250" "12500" "125000"
	   "15" "150" "1500" "15000" "150000"
	   "2" "20" "200" "2000" "20000" "200000"
	   "2.500" "25" "250" "2500" "25000" "250000"
	   "3" "30" "300" "3000" "30000" "300000"
	   "4" "40" "400" "4000" "40000" "400000"
	   "5" "50" "500" "5000" "50000" "500000"
	   "7.500" "75" "750" "7500" "75000" "750000"
	 )
      )
      (setq open_file (open (strcat cnp_root "/config/reg_scale.txt") "w" "utf8"))
      (foreach n reg_scale_list
	(write-line n open_file)
      )
      (close open_file)
    )
  )
  (cn7_rscale)
)


;******************************************************************************
;Verifica se o desenho está configurado....
;******************************************************************************
(defun cn7_init ()
  (setvar "cmdecho" 0)
  (if
    (and
	    (or
	      (and
		(/= 1.0 (getvar "userr4"))
	        (/= 100.0 (getvar "userr4"))
		(/= 1000.0 (getvar "userr4"))
	      )
	      (and
		(/= 1.0 (getvar "userr5"))
		(/= 100.0 (getvar "userr5"))
		(/= 1000.0 (getvar "userr5"))
	      )
	    );or
	    (/= (strcase (substr (getvar "dwgname") 1 7) T) "drawing")
    )
    (progn
      (cn7_alert_yes_no
	"O Cadnorma não está configurado"
	"para este desenho."
	"Deseja configurá-lo agora?")
      (if (= alert_resp "yes") (cn7_cfg_main))
    )
  )
);defun

;******************************************************************************
;preferências de carregamento - Autoload e Teclado
;******************************************************************************
(defun c:prf ()
  (cn7_autoload_file)
  (cn7_autoload)
  (princ)
)

;lê os parâmetros iniciais no arquivo
(defun cn7_autoload_file ()
  (if (not (findfile (strcat cnp_root "/config/autoload.txt")))
    (progn
      (setq file (open (strcat cnp_root "/config/autoload.txt") "w" "utf8"))
      (write-line "2" file)
      (write-line "2" file)
      (close file)
    )
  )
  ;lê as condições de carregamento
  (setq	file (open (strcat cnp_root "/config/autoload.txt") "r" "utf8"))
  (setq cn7_autoload_load (read-line file))
  (setq cn7_autoload_short (read-line file))
  (close file)
)

;função principal de autocarregamento  
(defun cn7_autoload ()
  (setq dcl_id (load_dialog (strcat cnp_root "/lisp/cadnorma.dcl")))
  (if (not (new_dialog "cn7_cfg_pref" dcl_id)) (exit))
  ;carregamento cadnorma
  (cond
    ((= cn7_autoload_load "0")
     (set_tile "cn7_pref_loadask" "cn7_pref_load_yes")
    )
    ((= cn7_autoload_load "1")
     (set_tile "cn7_pref_loadask" "cn7_pref_load_ask")
    )
    ((= cn7_autoload_load "2")
     (set_tile "cn7_pref_loadask" "cn7_pref_load_no")
    )
  )
  (action_tile "cn7_pref_loadask" "(prefload_ask)")
  	;define a variável de carregamento
  	(defun prefload_ask ()
	  (setq prefload_askvar $value)
	  (cond
	    ((= prefload_askvar "cn7_pref_load_yes") (setq cn7_autoload_load "0"))
	    ((= prefload_askvar "cn7_pref_load_ask") (setq cn7_autoload_load "1"))
	    ((= prefload_askvar "cn7_pref_load_no") (setq cn7_autoload_load "2"))
	  )
	)
  ;comandos de teclado
  (cond
    ((= cn7_autoload_short "0")
     (set_tile "cn7_pref_shortcut" "cn7_pref_short0")
    )
    ((= cn7_autoload_short "1")
     (set_tile "cn7_pref_shortcut" "cn7_pref_short1")
    )
    ((= cn7_autoload_short "2")
     (set_tile "cn7_pref_shortcut" "cn7_pref_short2")
    )
  )
  (action_tile "cn7_pref_shortcut" "(prefload_short)")
  	;define a variável de teclado
  	(defun prefload_short ()
	  (setq prefload_shortvar $value)
	  (cond
	    ((= prefload_shortvar "cn7_pref_short0") (setq cn7_autoload_short "0"))
	    ((= prefload_shortvar "cn7_pref_short1") (setq cn7_autoload_short "1"))
	    ((= prefload_shortvar "cn7_pref_short2") (setq cn7_autoload_short "2"))
	  )
	)
  ;demais ações
  (action_tile "cn7_pref_editshort" "(done_dialog 2)")
  (action_tile "cn7_pref_resetshort" "(done_dialog 3)")  
  (action_tile "cancel" "(done_dialog 0)")
  (action_tile "accept" "(done_dialog 1)")
  (setq cn_autoload_dialog (start_dialog))
  (unload_dialog dcl_id)
  (if (= 3 cn_autoload_dialog)
    (progn
      (cn7_alert_yes_no
	"Deseja realmente restaurar"
	"os atalhos originais do Cadnorma?"
	"Modificações feitas serão perdidas!"
      )
      (if (= alert_resp "yes")
	(cnp:copy-overwrite (strcat cnp_root "/lisp/shortcut.lsp") (strcat cnp_root "/lisp/teclado.lsp"))
      )
    );progn
  );if   
  (if (= 2 cn_autoload_dialog) (cnp:edit-shortcuts))
  (if (= 1 cn_autoload_dialog) (cn7_autoload_ok))
);defun

;acionado OK, grava o arquivo!
(defun cn7_autoload_ok ()
  (setq file (open (strcat cnp_root "/config/autoload.txt") "w" "utf8"))
  (write-line cn7_autoload_load file)
  (write-line cn7_autoload_short file)
  (close file)
)


;******************************************************************************
;comando de configuração do desenho
;******************************************************************************
(defun c:cfg ()
  (cn7_cfg_main)
  (princ)
)

;******************************************************************************
;função principal de configuração
;******************************************************************************
(defun cn7_cfg_main ()
  (setq cn7_dwgspace 1
	cn7_cfgmain_return 0)
  ;inicializando caixa de diálogo
  (setq dcl_id (load_dialog (strcat cnp_root "/lisp/cadnorma.dcl")))
  (if (not (new_dialog "cnp_cfg_main" dcl_id)) (exit))
  ;lê os parâmetros iniciais
  (start_list "cn10_radio_space") (mapcar 'add_list '("Model Space" "Layout (Paper Space)")) (end_list)
  (start_list "cn7_cfgmain_dwgunit") (mapcar 'add_list '("metros" "centímetros" "milímetros")) (end_list)
  (start_list "cn7_cfgmain_dimunit") (mapcar 'add_list '("metros" "centímetros" "milímetros")) (end_list)
  (cn7_cfg_defaults)
  (action_tile "cn10_radio_space" "(cn10_cfgmain_space)")
  	(defun cn10_cfgmain_space () (setq cfgdata_app_space $value))
  (action_tile "cn7_cfgmain_dwgunit" "(cn7_cfgmain_dwgunit)")
      (defun cn7_cfgmain_dwgunit () (setq cfgdata_dwgunit $value cfgdata_dimunit $value) (set_tile "cn7_cfgmain_dimunit" $value))
  ;Escolha da unidade de cotagem
  (action_tile "cn7_cfgmain_dimunit" "(cn7_dcl_dimunit)")
  	(defun cn7_dcl_dimunit () (setq cfgdata_dimunit $value))
  ;toggle limits
  (action_tile "cn7_toggle_limits" "(cfgmain_toggle_limits_action)")
  (action_tile "cancel" "(done_dialog 0)")
  (action_tile "accept" "(done_dialog 1)")
  (action_tile "cn7_cfg_pref_limits" "(done_dialog 2)")
  (action_tile "cn7_cfg_pref_text" "(done_dialog 3)")
  (action_tile "cn7_cfg_pref_dim" "(done_dialog 4)")
  (action_tile "cn7_cfg_pref_layer" "(done_dialog 5)")
  (setq cn_cfgmain_dialog (start_dialog))
  (unload_dialog dcl_id)
  (if (= 1 cn_cfgmain_dialog) (cn7_cfgmain_ok))
  (if (= 2 cn_cfgmain_dialog)
    (progn
      (cn7_cfgmain_savecfg)
      (setq cn7_cfgmain_return 1)
      (cn7_cfgmain_limits)
    )
  )
  (if (= 3 cn_cfgmain_dialog)
    (progn
      (cn7_cfgmain_savecfg)
      (setq cn7_cfgmain_return 1)
      (cn7_cfgmain_text)
    )
  )
  (if (= 4 cn_cfgmain_dialog)
    (progn
      (cn7_cfgmain_savecfg)
      (setq cn7_cfgmain_return 1)
      (cn7_cfgmain_dim)
    )
  )
  (if (= 5 cn_cfgmain_dialog)
    (progn
      (cn7_cfgmain_savecfg)
      (setq cn7_cfgmain_return 1)
      (cn7_cfgmain_layer)
    )
  )
);defun


;ação do botão limites
(defun cfgmain_toggle_limits_action ()
;;;  (setq denio $value)
  (setq cfgdata_app_limits $value)
  (if (= "1" cfgdata_app_limits)
    (progn
      (setq cfgdata_app_limits "1")
      (mode_tile "cn7_cfg_pref_limits" 1)
    )
    (progn
      (setq cfgdata_app_limits "0")
      (mode_tile "cn7_cfg_pref_limits" 0)
    )
  )
;;;  (cn7_cfgmain_savecfg)
)

;********************************************************
;lê os parâmetros iniciais
;********************************************************
(defun cn7_cfg_defaults ()
  (if (not (findfile (strcat cnp_root "/config/config.txt")))
    (progn
      (setq file1 (open (strcat cnp_root "/config/config.txt") "w" "utf8"))
      (repeat 7
	(write-line "0" file1)
      )
      (close file1)
    )
  )
  (setq file1 (open (strcat cnp_root "/config/config.txt") "r" "utf8")
	cfgdata_dwgunit (read-line file1)
	cfgdata_dimunit (read-line file1)
	cfgdata_app_limits (read-line file1)
	cfgdata_app_text (read-line file1)
	cfgdata_app_dim (read-line file1)
	cfgdata_app_layer (read-line file1)
	cfgdata_app_space (read-line file1)
  )
  (close file1)
  ;vai setar os defaults na caixa de diálogo
  (cond
    ((= "0" cfgdata_dwgunit) (set_tile "cn7_cfgmain_dwgunit" "0"))
    ((= "1" cfgdata_dwgunit) (set_tile "cn7_cfgmain_dwgunit" "1"))
    ((= "2" cfgdata_dwgunit) (set_tile "cn7_cfgmain_dwgunit" "2"))
  )
  (cond
    ((= "0" cfgdata_dimunit) (set_tile "cn7_cfgmain_dimunit" "0"))
    ((= "1" cfgdata_dimunit) (set_tile "cn7_cfgmain_dimunit" "1"))
    ((= "2" cfgdata_dimunit) (set_tile "cn7_cfgmain_dimunit" "2"))
  )
  (cond
    ((= "0" cfgdata_app_space) (set_tile "cn10_radio_space" "0"))
    ((= "1" cfgdata_app_space) (set_tile "cn10_radio_space" "1"))
  )
  (cond
    ((= "0" cfgdata_app_limits) (set_tile "cn7_toggle_limits" "0"))
    ((= "1" cfgdata_app_limits) (set_tile "cn7_toggle_limits" "1"))
  )
)
  

;salva o arquivo de defaults
(defun cn7_cfgmain_savecfg ()
  (setq file1 (open (strcat cnp_root "/config/config.txt") "w" "utf8"))
  (write-line cfgdata_dwgunit file1)
  (write-line cfgdata_dimunit file1)
  (write-line cfgdata_app_limits file1)
  (write-line cfgdata_app_text file1)
  (write-line cfgdata_app_dim file1)
  (write-line cfgdata_app_layer file1)
  (write-line cfgdata_app_space file1)
  (close file1)
)



;***********************************************************
;Botão "Layers"
;***********************************************************
(defun c:allay () (setq cn7_cfgmain_return 0) (cn7_cfgmain_layer) (princ))

;distribuidor
(defun cn7_cfgmain_layer ()
  (cn7_cfg_allayer_files)
  (cn7_cfg_allayer)
  (if (= cn7_cfgmain_return 1) (cn7_cfg_main))
)

;lê os dados iniciais da DCL no arquivo de dados
(defun cn7_cfg_allayer_files ()
  (if (not (findfile (strcat cnp_root "/config/allayer.txt")))
    (progn
      (setq file (open (strcat cnp_root "/config/allayer.txt") "w" "utf8"))
      (write-line "0" file);allayer_create
      (write-line "0" file);allayer_project
      (write-line "1" file);allayer_cdn_txtlay
      (write-line "1" file);allayer_cus_txtlay
      (write-line "1" file);allayer_cdn_dimlay
      (write-line "1" file);allayer_cus_dimlay
      (close file)
    )
  )
  ;procura o valor padrão
  (setq	file (open (strcat cnp_root "/config/allayer.txt") "r" "utf8"))
  (setq allayer_create (read-line file))
  (setq allayer_project (read-line file))
  (setq allayer_cdn_txtlay (read-line file))
  (setq allayer_cus_txtlay (read-line file))
  (setq allayer_cdn_dimlay (read-line file))
  (setq allayer_cus_dimlay (read-line file))
  (close file)
)

;função principal
(defun cn7_cfg_allayer ()
;abre a dcl(write-line allayer_project file)
  (setq allayer_projlist
	 (list"Geral" "Arquitetura" "Paisagismo"
	      "Urbanismo" "Elétrica" "Telefone"
	      "Rede Lógica" "Água" "Esgoto"
	      "Incêndio" "Aterramento" "Ar Condicionado"
	      "Concreto" "Metálica" "Gás"
	      "Automação" "Alarme" "CFTV"
	      "Som" "Topografia" "User_01"
	      "User_02" "User_03"))
  (setq dcl_id (load_dialog (strcat cnp_root "/lisp/cadnorma.dcl")))
  (if (not (new_dialog "cn7_cfg_layers" dcl_id)) (exit))
  ;preenche a lista de projetos disponíveis
  (start_list "allayer_modelos")
  (mapcar 'add_list allayer_projlist)
  (end_list)
  (action_tile "allayer_modelos" "(setq allayer_project $value)")
  ;toggle create
  (if (= "0" allayer_create)
    (progn
      (set_tile "allay_create" "0")
      (mode_tile "allayer_modelos" 1)
    )
    (progn
      (set_tile "allay_create" "1")
      (mode_tile "allayer_modelos" 0)
      (set_tile "allayer_modelos" allayer_project)
    )
  )
  (action_tile "allay_create" "(allay_create_action)")
  	;ao selecionar o toggle create...
  	(defun allay_create_action ()
	  (setq allayer_create $value)
	  (if (= "0" allayer_create)
	    (progn
	      (mode_tile "allayer_modelos" 1)
	    )
	    (progn
	      (mode_tile "allayer_modelos" 0)
	      (set_tile "allayer_modelos" allayer_project)
	    )
	  )
	);defun	  
  ;toggle cadnorma_text
  (if (= "1" allayer_cdn_txtlay) (set_tile "allay_text_cadnorma" "1") (set_tile "allay_text_cadnorma" "0"))
  (action_tile "allay_text_cadnorma" "(setq allayer_cdn_txtlay $value)")
  ;toggle custom_text
  (if (= "1" allayer_cus_txtlay) (set_tile "allay_text_custom" "1") (set_tile "allay_text_custom" "0"))
  (action_tile "allay_text_custom" "(setq allayer_cus_txtlay $value)")
  ;toggle cadnoma_dim
  (if (= "1" allayer_cdn_dimlay) (set_tile "allay_dim_cadnorma" "1") (set_tile "allay_dim_cadnorma" "0"))
  (action_tile "allay_dim_cadnorma" "(setq allayer_cdn_dimlay $value)")
  ;toggle custom_dim
  (if (= "1" allayer_cus_dimlay) (set_tile "allay_dim_custom" "1") (set_tile "allay_dim_custom" "0"))
  (action_tile "allay_dim_custom" "(setq allayer_cus_dimlay $value)")
  (action_tile "accept" "(done_dialog 1)")
  (action_tile "cancel" "(done_dialog 0)")
  (setq cn_allayer_dialog (start_dialog))
  (unload_dialog dcl_id)
;o que fazer depois
  (if (= 1 cn_allayer_dialog) (cn7_allayer_ok))
)

;salva o arquivo de dados
(defun cn7_allayer_ok ()
  (setq file (open (strcat cnp_root "/config/allayer.txt") "w" "utf8"))
  (write-line allayer_create file)
  (write-line allayer_project file)
  (write-line allayer_cdn_txtlay file)
  (write-line allayer_cus_txtlay file)
  (write-line allayer_cdn_dimlay file)
  (write-line allayer_cus_dimlay file)
  (close file)
  (setq cdn_txt (fix (distof allayer_cdn_txtlay))
	cut_txt (fix (distof allayer_cus_txtlay))
	cdn_dim (fix (distof allayer_cdn_dimlay))
	cus_txt (fix (distof allayer_cus_dimlay))
  )
)

;configura o desenho atual
(defun cn7_dwg_allayer ()
  (cn7_cfg_allayer_files) ; lê as variáveis iniciais
  (if (= "1" allayer_create)
    (cond
      ((= "0" allayer_project)
       (command "._insert" (strcat cnp_root "/modelos/cadnorma_geral") "0,0" "" "" "" "._erase" (entlast) ""  "._purge" "_b" "cadnorma_geral" "n"))
      ((= "1" allayer_project)
       (command "._insert" (strcat cnp_root "/modelos/cadnorma_arquitetura") "0,0" "" "" "" "._erase" (entlast) ""  "._purge" "_b" "cadnorma_arquitetura" "n"))
      ((= "2" allayer_project)
       (command "._insert" (strcat cnp_root "/modelos/cadnorma_paisagismo") "0,0" "" "" "" "._erase" (entlast) ""  "._purge" "_b" "cadnorma_paisagismo" "n"))
      ((= "3" allayer_project)
       (command "._insert" (strcat cnp_root "/modelos/cadnorma_urbanismo") "0,0" "" "" "" "._erase" (entlast) ""  "._purge" "_b" "cadnorma_urbanismo" "n"))
      ((= "4" allayer_project)
       (command "._insert" (strcat cnp_root "/modelos/cadnorma_elétrica") "0,0" "" "" "" "._erase" (entlast) ""  "._purge" "_b" "cadnorma_elétrica" "n"))
      ((= "5" allayer_project)
       (command "._insert" (strcat cnp_root "/modelos/cadnorma_telefone") "0,0" "" "" "" "._erase" (entlast) ""  "._purge" "_b" "cadnorma_telefone" "n"))
      ((= "6" allayer_project)
       (command "._insert" (strcat cnp_root "/modelos/cadnorma_lógica") "0,0" "" "" "" "._erase" (entlast) ""  "._purge" "_b" "cadnorma_lógica" "n"))
      ((= "7" allayer_project)
       (command "._insert" (strcat cnp_root "/modelos/cadnorma_água") "0,0" "" "" "" "._erase" (entlast) ""  "._purge" "_b" "cadnorma_água" "n"))
      ((= "8" allayer_project)
       (command "insert" (strcat cnp_root "/modelos/cadnorma_esgoto") "0,0" "" "" "" "._erase" (entlast) ""  "._purge" "_b" "cadnorma_esgoto" "n"))
      ((= "9" allayer_project)
       (command "._insert" (strcat cnp_root "/modelos/cadnorma_incêndio") "0,0" "" "" "" "._erase" (entlast) ""  "._purge" "_b" "cadnorma_incêndio" "n"))
      ((= "10" allayer_project)
       (command "._insert" (strcat cnp_root "/modelos/cadnorma_aterramento") "0,0" "" "" "" "._erase" (entlast) ""  "._purge" "_b" "cadnorma_aterramento" "n"))
      ((= "11" allayer_project)
       (command "._insert" (strcat cnp_root "/modelos/cadnorma_ar_condicionado") "0,0" "" "" "" "._erase" (entlast) ""  "._purge" "_b" "cadnorma_ar_condicionado" "n"))
      ((= "12" allayer_project)
       (command "._insert" (strcat cnp_root "/modelos/cadnorma_concreto") "0,0" "" "" "" "._erase" (entlast) ""  "._purge" "_b" "cadnorma_concreto" "n"))
      ((= "13" allayer_project)
       (command "._insert" (strcat cnp_root "/modelos/cadnorma_metálica") "0,0" "" "" "" "._erase" (entlast) ""  "._purge" "_b" "cadnorma_metálica" "n"))
      ((= "14" allayer_project)
       (command "._insert" (strcat cnp_root "/modelos/cadnorma_gás") "0,0" "" "" "" "._erase" (entlast) ""  "._purge" "_b" "cadnorma_gás" "n"))
      ((= "15" allayer_project)
       (command "._insert" (strcat cnp_root "/modelos/cadnorma_automação") "0,0" "" "" "" "._erase" (entlast) ""  "._purge" "_b" "cadnorma_automação" "n"))
      ((= "16" allayer_project)
       (command "._insert" (strcat cnp_root "/modelos/cadnorma_alarme") "0,0" "" "" "" "._erase" (entlast) ""  "._purge" "_b" "cadnorma_alarme" "n"))
      ((= "17" allayer_project)
       (command "._insert" (strcat cnp_root "/modelos/cadnorma_cftv") "0,0" "" "" "" "._erase" (entlast) ""  "._purge" "_b" "cadnorma_cftv" "n"))
      ((= "18" allayer_project)
       (command "._insert" (strcat cnp_root "/modelos/cadnorma_som") "0,0" "" "" "" "._erase" (entlast) ""  "._purge" "_b" "cadnorma_som" "n"))
      ((= "19" allayer_project)
       (command "._insert" (strcat cnp_root "/modelos/cadnorma_topografia") "0,0" "" "" "" "._erase" (entlast) ""  "._purge" "_b" "cadnorma_topografia" "n"))
      ((= "20" allayer_project)
       (command "._insert" (strcat cnp_root "/modelos/cadnorma_user01") "0,0" "" "" "" "._erase" (entlast) ""  "._purge" "_b" "cadnorma_user01" "n"))
      ((= "21" allayer_project)
       (command "._insert" (strcat cnp_root "/modelos/cadnorma_user02") "0,0" "" "" "" "._erase" (entlast) ""  "._purge" "_b" "cadnorma_user02" "n"))
      ((= "22" allayer_project)
       (command "._insert" (strcat cnp_root "/modelos/cadnorma_user03") "0,0" "" "" "" "._erase" (entlast) ""  "._purge" "_b" "cadnorma_user03" "n"))
      (t (alert "Nenhum projeto Selecionado!"))
    );cond
  );if
  (cond 
    ((and (= allayer_cdn_txtlay "1") (= allayer_cus_txtlay "1")) (setvar "useri5" 0) (setq cdn_txt 1 cus_txt 1))
    ((and (= allayer_cdn_txtlay "1") (= allayer_cus_txtlay "0")) (setvar "useri5" 1) (setq cdn_txt 1 cus_txt 0))
    ((and (= allayer_cdn_txtlay "0") (= allayer_cus_txtlay "1")) (setvar "useri5" 2) (setq cdn_txt 0 cus_txt 1))
    ((and (= allayer_cdn_txtlay "0") (= allayer_cus_txtlay "0")) (setvar "useri5" 3) (setq cdn_txt 0 cus_txt 0))
  ) 
  (cond
    ((and (= allayer_cdn_dimlay "1") (= allayer_cus_dimlay "1")) (setvar "useri4" 0) (setq cdn_dim 1 cus_dim 1))
    ((and (= allayer_cdn_dimlay "1") (= allayer_cus_dimlay "0")) (setvar "useri4" 1) (setq cdn_dim 1 cus_dim 0))
    ((and (= allayer_cdn_dimlay "0") (= allayer_cus_dimlay "1")) (setvar "useri4" 2) (setq cdn_dim 0 cus_dim 1))
    ((and (= allayer_cdn_dimlay "0") (= allayer_cus_dimlay "0")) (setvar "useri4" 3) (setq cdn_dim 0 cus_dim 0))
  )
)

;***********************************************************
;Botão "Cotas"
;***********************************************************
(defun c:aldim () (setq cn7_cfgmain_return 0) (cn7_cfgmain_dim) (princ))

;distribuidor
(defun cn7_cfgmain_dim ()
  (cn7_cfg_aldim_file)
  (cn7_cfg_aldim)
  (if (= cn7_cfgmain_return 1) (cn7_cfg_main))
)

;lê os dados iniciais da DCL no arquivo de dados
(defun cn7_cfg_aldim_file ()
  (if (findfile (strcat cnp_root "/config/aldim.txt"))
    (cn7_aldim_readfile)
    (progn
      (setq file (open (strcat cnp_root "/config/aldim.txt") "w" "utf8"))
      (write-line "0" file)
      (write-line "4" file)
      (write-line "1" file)
      (write-line "2" file)
      (write-line "2" file)
      (write-line "0" file)
      (write-line "2" file)
      (write-line "1" file)
      (close file)
      (cn7_aldim_readfile)
    )
  )
)

;função que lê o arquivo de dados
(defun cn7_aldim_readfile ()
  (setq	file (open (strcat cnp_root "/config/aldim.txt") "r" "utf8"))
  (setq	aldim_blk1 (read-line file))
  (setq	aldim_blk2 (read-line file))
  (setq	aldim_txst (read-line file))
  (setq	aldim_dzin (read-line file))
  (setq	aldim_ddec (read-line file))
  (setq	aldim_dsep (read-line file))
  (setq	aldim_tcol (read-line file))
  (setq	aldim_dcol (read-line file))
  (close file)
)

(defun cn7_cfg_aldim ()
;abre a dcl
  (setq dcl_id (load_dialog (strcat cnp_root "/lisp/cadnorma.dcl")))
  (if (not (new_dialog "cn7_cfg_aldim" dcl_id)) (exit))
  ;inutilização dos slides
  (mode_tile "aldim_linear_img" 1)
  (mode_tile "aldim_angular_img" 1)
  ;Lineares
  (setq cn7_cfg_aldim_blk (list "Archtick" "Dot" "Open30" "Open90" "Closed Filled" "Tick"))
  (start_list "aldim_linear_popup")
  (mapcar 'add_list cn7_cfg_aldim_blk)
  (end_list)
  (set_tile "aldim_linear_popup" aldim_blk1)
  (setq x (dimx_tile "aldim_linear_img") y (dimy_tile "aldim_linear_img"))
  (start_image "aldim_linear_img")
  (fill_image 0 0 x y -2)
  (end_image)
  (start_image "aldim_linear_img")
  (cond
    ((= "0" aldim_blk1) (slide_image 0 0 x y (strcat cnp_root "/slides/aldim_archtick.sld")))
    ((= "1" aldim_blk1) (slide_image 0 0 x y (strcat cnp_root "/slides/aldim_dot.sld")))
    ((= "2" aldim_blk1) (slide_image 0 0 x y (strcat cnp_root "/slides/aldim_open30.sld")))
    ((= "3" aldim_blk1) (slide_image 0 0 x y (strcat cnp_root "/slides/aldim_open90.sld")))
    ((= "4" aldim_blk1) (slide_image 0 0 x y (strcat cnp_root "/slides/aldim_closed.sld")))
    ((= "5" aldim_blk1) (slide_image 0 0 x y (strcat cnp_root "/slides/aldim_tick.sld")))
  )
  (end_image)
  (action_tile "aldim_linear_popup" "(aldim_poplin_updslide)")

  ;angulares
  (start_list "aldim_angular_popup")
  (mapcar 'add_list cn7_cfg_aldim_blk)
  (end_list)
  (set_tile "aldim_angular_popup" aldim_blk2)
  (setq x (dimx_tile "aldim_angular_img") y (dimy_tile "aldim_angular_img"))
  (start_image "aldim_angular_img")
  (fill_image 0 0 x y -2)
  (end_image)
  (start_image "aldim_angular_img")
  (cond
    ((= "0" aldim_blk2) (slide_image 0 0 x y (strcat cnp_root "/slides/aldim_archtick.sld")))
    ((= "1" aldim_blk2) (slide_image 0 0 x y (strcat cnp_root "/slides/aldim_dot.sld")))
    ((= "2" aldim_blk2) (slide_image 0 0 x y (strcat cnp_root "/slides/aldim_open30.sld")))
    ((= "3" aldim_blk2) (slide_image 0 0 x y (strcat cnp_root "/slides/aldim_open90.sld")))
    ((= "4" aldim_blk2) (slide_image 0 0 x y (strcat cnp_root "/slides/aldim_closed.sld")))
    ((= "5" aldim_blk2) (slide_image 0 0 x y (strcat cnp_root "/slides/aldim_tick.sld")))
  )
  (end_image)
  (action_tile "aldim_angular_popup" "(aldim_popang_updslide)")
  
  ;lista de estilos
  (setq aldim_stylist (list "r50" "r60" "r70" "r80" "r90" "r100" "r120" "r140" "r175" "r200"
			    "t1" "t2" "t3" "t4" "t5" "t6" "t7"))
  (start_list "aldim_txt_sty")
  (mapcar 'add_list aldim_stylist)
  (end_list)
  (set_tile "aldim_txt_sty" aldim_txst)
  (action_tile "aldim_txt_sty" "(setq aldim_txst $value)")

  ;lista de Supressão de zeros
  (setq aldim_zerlist (list "à esquerda" "à direita" "ambos" "nenhum"))
  (start_list "aldim_txt_zer")
  (mapcar 'add_list aldim_zerlist)
  (end_list)
  (set_tile "aldim_txt_zer" aldim_dzin)
  (action_tile "aldim_txt_zer" "(setq aldim_dzin $value)")

  ;Número de Casas Decimais
  (setq aldim_declist (list "0" "0.0" "0.00" "0.000" "0.0000" "0.00000"
			     "0.000000" "0.0000000" "0.00000000"))
  (start_list "aldim_txt_dec")
  (mapcar 'add_list aldim_declist)
  (end_list)
  (set_tile "aldim_txt_dec" aldim_ddec)
  (action_tile "aldim_txt_dec" "(setq aldim_ddec $value)")

  ;Separador de Decimais
  (setq aldim_seplist (list "Ponto" "Vírgula"))
  (start_list "aldim_txt_sep")
  (mapcar 'add_list aldim_seplist)
  (end_list)
  (set_tile "aldim_txt_sep" aldim_dsep)
  (action_tile "aldim_txt_sep" "(setq aldim_dsep $value)")

  ;cor do texto
  (start_image "aldim_txt_color")
  (fill_image  0  0
    (dimx_tile "aldim_txt_color")
    (dimy_tile "aldim_txt_color")
    (fix (distof aldim_tcol))
  )
  (end_image)
  (action_tile "aldim_txt_color" "(aldim_txcol)")

  ;cor das linhas
  (start_image "aldim_lines_color")
  (fill_image  0  0
    (dimx_tile "aldim_lines_color")
    (dimy_tile "aldim_lines_color")
    (fix (distof aldim_dcol))
  )
  (end_image)
  (action_tile "aldim_lines_color" "(aldim_lncol)")

  (action_tile "accept" "(done_dialog 1)")
  (action_tile "cancel" "(done_dialog 0)")
  (setq cn_aldim_dialog (start_dialog))
  (unload_dialog dcl_id)
;o que fazer depois
  (if (= 1 cn_aldim_dialog) (cn7_aldim_ok))
)


;***************************************************
;botão "OK"
;salva o arquivo
;***************************************************
(defun cn7_aldim_ok ()
  (setq file2 (open (strcat cnp_root "/config/aldim.txt") "w" "utf8"))
  (write-line aldim_blk1 file2)
  (write-line aldim_blk2 file2)
  (write-line aldim_txst file2)
  (write-line aldim_dzin file2)
  (write-line aldim_ddec file2)
  (write-line aldim_dsep file2)
  (write-line aldim_tcol file2)
  (write-line aldim_dcol file2)
  (close file2)
)

;escolher cor das linhas
(defun aldim_lncol ()
  (setq aldim_newcol (acad_colordlg (fix (distof aldim_dcol))))
  (if (/= nil aldim_newcol) (setq aldim_dcol (rtos aldim_newcol 2 0)))  
  (start_image "aldim_lines_color")
  (fill_image  0  0
    (dimx_tile "aldim_lines_color")
    (dimy_tile "aldim_lines_color")
    (fix (distof aldim_dcol))
  )
  (end_image)
)

;escolher cor do texto
(defun aldim_txcol ()
  (setq aldim_newcol (acad_colordlg (fix (distof aldim_tcol))))
  (if (/= nil aldim_newcol) (setq aldim_tcol (rtos aldim_newcol 2 0)))
  (start_image "aldim_txt_color")
  (fill_image  0  0
    (dimx_tile "aldim_txt_color")
    (dimy_tile "aldim_txt_color")
    (fix (distof aldim_tcol))
  )
  (end_image)
)


;atualizar slide linear
(defun aldim_poplin_updslide ()
  (setq aldim_blk1 $value)
  (setq x (dimx_tile "aldim_linear_img") y (dimy_tile "aldim_linear_img"))
  (start_image "aldim_linear_img")
  (fill_image 0 0 x y -2)
  (end_image)
  (start_image "aldim_linear_img")
  (cond
    ((= "0" aldim_blk1) (slide_image 0 0 x y (strcat cnp_root "/slides/aldim_archtick.sld")))
    ((= "1" aldim_blk1) (slide_image 0 0 x y (strcat cnp_root "/slides/aldim_dot.sld")))
    ((= "2" aldim_blk1) (slide_image 0 0 x y (strcat cnp_root "/slides/aldim_open30.sld")))
    ((= "3" aldim_blk1) (slide_image 0 0 x y (strcat cnp_root "/slides/aldim_open90.sld")))
    ((= "4" aldim_blk1) (slide_image 0 0 x y (strcat cnp_root "/slides/aldim_closed.sld")))
    ((= "5" aldim_blk1) (slide_image 0 0 x y (strcat cnp_root "/slides/aldim_tick.sld")))
  )
  (end_image)
)

;atualizar slide angular
(defun aldim_popang_updslide ()
  (setq aldim_blk2 $value)
  (setq x (dimx_tile "aldim_angular_img") y (dimy_tile "aldim_angular_img"))
  (start_image "aldim_angular_img")
  (fill_image 0 0 x y -2)
  (end_image)
  (start_image "aldim_angular_img")
  (cond
    ((= "0" aldim_blk2) (slide_image 0 0 x y (strcat cnp_root "/slides/aldim_archtick.sld")))  
    ((= "1" aldim_blk2) (slide_image 0 0 x y (strcat cnp_root "/slides/aldim_dot.sld")))
    ((= "2" aldim_blk2) (slide_image 0 0 x y (strcat cnp_root "/slides/aldim_open30.sld")))
    ((= "3" aldim_blk2) (slide_image 0 0 x y (strcat cnp_root "/slides/aldim_open90.sld")))
    ((= "4" aldim_blk2) (slide_image 0 0 x y (strcat cnp_root "/slides/aldim_closed.sld")))
    ((= "5" aldim_blk2) (slide_image 0 0 x y (strcat cnp_root "/slides/aldim_tick.sld")))
  )
  (end_image)
)

;***********************************************************
;Botão "textos"
;***********************************************************
(defun c:altext () (setq cn7_cfgmain_return 0) (cn7_cfgmain_text) (princ))

(defun cn7_cfgmain_text ()
  (cn7_cfg_altext_file)
  (cn7_cfg_altext)
  (if (= cn7_cfgmain_return 1) (cn7_cfg_main))
)

;lê os dados iniciais da DCL no arquivo de dados
(defun cn7_cfg_altext_file ()
  (if (findfile (strcat cnp_root "/config/altext.txt"))
    (cn7_altext_readfile)
    (progn
      (setq file (open (strcat cnp_root "/config/altext.txt") "w" "utf8"))
      (write-line "Arial;1.5;1" file)
      (write-line "Arial;2.0;1" file)
      (write-line "Arial;2.5;2" file)
      (write-line "Arial;3.0;2" file)
      (write-line "Arial;3.5;4" file)
      (write-line "Arial;5.0;5" file)
      (write-line "Arial;7.0;6" file)
      (close file)
      (cn7_altext_readfile)
    )
  )
)


;função que lê o arquivo de dados
(defun cn7_altext_readfile ()
  (setq	file (open (strcat cnp_root "/config/altext.txt") "r" "utf8"))
  (setq	linha (read-line file))
  (altext_separa_dados)
  (setq t1_font cn7_dado1
	t1_alt cn7_dado2
	t1_col cn7_dado3)
  (setq	linha (read-line file))
  (altext_separa_dados)
  (setq t2_font cn7_dado1
	t2_alt cn7_dado2
	t2_col cn7_dado3)
  (setq	linha (read-line file))
  (altext_separa_dados)
  (setq t3_font cn7_dado1
	t3_alt cn7_dado2
	t3_col cn7_dado3)
  (setq	linha (read-line file))
  (altext_separa_dados)
  (setq t4_font cn7_dado1
	t4_alt cn7_dado2
	t4_col cn7_dado3)
  (setq	linha (read-line file))
  (altext_separa_dados)
  (setq t5_font cn7_dado1
	t5_alt cn7_dado2
	t5_col cn7_dado3)
  (setq	linha (read-line file))
  (altext_separa_dados)
  (setq t6_font cn7_dado1
	t6_alt cn7_dado2
	t6_col cn7_dado3)
  (setq	linha (read-line file))
  (altext_separa_dados)
  (setq t7_font cn7_dado1
	t7_alt cn7_dado2
	t7_col cn7_dado3)
  (close file)
)


(defun cn7_cfg_altext ()
;abre a dcl
  (setq dcl_id (load_dialog (strcat cnp_root "/lisp/cadnorma.dcl")))
  (if (not (new_dialog "cn7_cfg_altext" dcl_id)) (exit))
  ;preenche a lista de estilos
  (setq cn7_cfg_altext_styles (list "T1" "T2" "T3" "T4" "T5" "T6" "T7"))
  (start_list "cn7_cfg_altext_stylist")
  (mapcar 'add_list cn7_cfg_altext_styles)
  (end_list)
  (setq cn7_cfg_altext_fonts (list
			     "Arial" "Arial Black" "CityBlueprint" "Comic Sans"
			     "italic" "Romans" "Scriptc" "Simplex" "Times New Roman"
			     "Verdana" "Technic" "Isocpeur"))
  (start_list "cn7_cfg_altext_fontpop")
  (mapcar 'add_list cn7_cfg_altext_fonts)
  (end_list)
  (mode_tile "cn7_cfg_altext_fontpop" 1)
  (mode_tile "altext_color_img" 1)
  (mode_tile "altext_edit_altura" 1)  
  (action_tile "cn7_cfg_altext_stylist" "(cn7_cfg_altext_stylist_update)")
  (action_tile "cn7_cfg_altext_fontpop" "(tx_popfont)")
  (action_tile "altext_edit_altura" "(altext_altura)")
  (action_tile "altext_color_img" "(altext_color)")
  (action_tile "accept" "(done_dialog 1)")
  (action_tile "cancel" "(done_dialog 0)")
  (setq cn_text_dialog (start_dialog))
  (unload_dialog dcl_id)
;o que fazer depois
  (if (= 1 cn_text_dialog) (cn7_text_ok))
)


(defun altext_color ()
  (setq altext_update_newcol (acad_colordlg (fix (distof altext_update_currcol))))
  (if (/= nil altext_update_newcol) (setq altext_update_currcol (rtos altext_update_newcol 2 0)))
  (start_image "altext_color_img")
  (fill_image  0  0
    (dimx_tile "altext_color_img")
    (dimy_tile "altext_color_img")
    (fix (distof altext_update_currcol))
  )
  (end_image)
  (cond
    ((= altext_curr_style_n "0") (setq t1_col altext_update_currcol))
    ((= altext_curr_style_n "1") (setq t2_col altext_update_currcol))
    ((= altext_curr_style_n "2") (setq t3_col altext_update_currcol))
    ((= altext_curr_style_n "3") (setq t4_col altext_update_currcol))
    ((= altext_curr_style_n "4") (setq t5_col altext_update_currcol))
    ((= altext_curr_style_n "5") (setq t6_col altext_update_currcol))
    ((= altext_curr_style_n "6") (setq t7_col altext_update_currcol))
  )
)


;define a altura do estilo.
(defun altext_altura ()
  (setq altext_alt $value)
  (if (not (distof altext_alt))
    (progn
      (alert "Valor Inválido\nEntre com um\nnúmero real...")
      (mode_tile "altext_edit_altura" 2)
    )
  )
  (cond
    ((= altext_curr_style_n "0") (setq t1_alt altext_alt))
    ((= altext_curr_style_n "1") (setq t2_alt altext_alt))
    ((= altext_curr_style_n "2") (setq t3_alt altext_alt))
    ((= altext_curr_style_n "3") (setq t4_alt altext_alt))
    ((= altext_curr_style_n "4") (setq t5_alt altext_alt))
    ((= altext_curr_style_n "5") (setq t6_alt altext_alt))
    ((= altext_curr_style_n "6") (setq t7_alt altext_alt))
  )
)


;ao selecionar um estilo, atualiza os dados
(defun cn7_cfg_altext_stylist_update ()
  (mode_tile "cn7_cfg_altext_fontpop" 0)
  (mode_tile "altext_color_img" 0)
  (mode_tile "altext_edit_altura" 0) 
  (setq altext_curr_style_n $value)
  (cond
    ((= altext_curr_style_n "0")
     (setq altext_update_currfnt t1_font
	   altext_update_curralt t1_alt
	   altext_update_currcol t1_col)
    )
    ((= altext_curr_style_n "1")
     (setq altext_update_currfnt t2_font
	   altext_update_curralt t2_alt
	   altext_update_currcol t2_col))
    ((= altext_curr_style_n "2")
     (setq altext_update_currfnt t3_font
	   altext_update_curralt t3_alt
	   altext_update_currcol t3_col))
    ((= altext_curr_style_n "3")
     (setq altext_update_currfnt t4_font
	   altext_update_curralt t4_alt
	   altext_update_currcol t4_col))
    ((= altext_curr_style_n "4")
     (setq altext_update_currfnt t5_font
	   altext_update_curralt t5_alt
	   altext_update_currcol t5_col))
    ((= altext_curr_style_n "5")
     (setq altext_update_currfnt t6_font
	   altext_update_curralt t6_alt
	   altext_update_currcol t6_col))
    ((= altext_curr_style_n "6")
     (setq altext_update_currfnt t7_font
	   altext_update_curralt t7_alt
	   altext_update_currcol t7_col))
    ((= altext_curr_style_n "7")
     (setq altext_update_currfnt t8_font
	   altext_update_curralt t8_alt
	   altext_update_currcol t8_col))
  );cond
  (altext_stylist_update)
)


(defun altext_stylist_update ()
  ;update poplist
  (cond
    ((= altext_update_currfnt "0") (set_tile "cn7_cfg_altext_fontpop" "0"))
    ((= altext_update_currfnt "1") (set_tile "cn7_cfg_altext_fontpop" "1"))
    ((= altext_update_currfnt "2") (set_tile "cn7_cfg_altext_fontpop" "2"))
    ((= altext_update_currfnt "3") (set_tile "cn7_cfg_altext_fontpop" "3"))
    ((= altext_update_currfnt "4") (set_tile "cn7_cfg_altext_fontpop" "4"))
    ((= altext_update_currfnt "5") (set_tile "cn7_cfg_altext_fontpop" "5"))
    ((= altext_update_currfnt "6") (set_tile "cn7_cfg_altext_fontpop" "6"))
    ((= altext_update_currfnt "7") (set_tile "cn7_cfg_altext_fontpop" "7"))
    ((= altext_update_currfnt "8") (set_tile "cn7_cfg_altext_fontpop" "8"))
    ((= altext_update_currfnt "9") (set_tile "cn7_cfg_altext_fontpop" "9"))
    ((= altext_update_currfnt "10") (set_tile "cn7_cfg_altext_fontpop" "10"))
    ((= altext_update_currfnt "11") (set_tile "cn7_cfg_altext_fontpop" "11"))
  )
  ;update slide
  (setq x (dimx_tile "altext_font_img") y (dimy_tile "altext_font_img"))
  (start_image "altext_font_img")
  (fill_image 0 0 x y -2)
  (end_image)
  (start_image "altext_font_img")
  (cond
    ((= altext_update_currfnt "0") (slide_image 0 0 x y (strcat cnp_root "/slides/altext_arial.sld")))
    ((= altext_update_currfnt "1") (slide_image 0 0 x y (strcat cnp_root "/slides/altext_arial_black.sld")))
    ((= altext_update_currfnt "2") (slide_image 0 0 x y (strcat cnp_root "/slides/altext_cityblueprint.sld")))
    ((= altext_update_currfnt "3") (slide_image 0 0 x y (strcat cnp_root "/slides/altext_comic.sld")))
    ((= altext_update_currfnt "4") (slide_image 0 0 x y (strcat cnp_root "/slides/altext_italic.sld")))
    ((= altext_update_currfnt "5") (slide_image 0 0 x y (strcat cnp_root "/slides/altext_romans.sld")))
    ((= altext_update_currfnt "6") (slide_image 0 0 x y (strcat cnp_root "/slides/altext_scriptc.sld")))
    ((= altext_update_currfnt "7") (slide_image 0 0 x y (strcat cnp_root "/slides/altext_simplex.sld")))
    ((= altext_update_currfnt "8") (slide_image 0 0 x y (strcat cnp_root "/slides/altext_times.sld")))
    ((= altext_update_currfnt "9") (slide_image 0 0 x y (strcat cnp_root "/slides/altext_verdana.sld")))
    ((= altext_update_currfnt "10") (slide_image 0 0 x y (strcat cnp_root "/slides/altext_technic.sld")))
    ((= altext_update_currfnt "11") (slide_image 0 0 x y (strcat cnp_root "/slides/altext_isocpeur.sld")))
  )
  (end_image)
  (set_tile "altext_edit_altura" altext_update_curralt)
  (setq x (dimx_tile "altext_color_img") y (dimy_tile "altext_color_img"))
  (start_image "altext_color_img")
  (fill_image 0 0 x y (fix (distof altext_update_currcol)))
  (end_image)
)


;definição da fonte
(defun tx_popfont ()
  (setq font_n $value)
  (altext_popfont)
  (altext_fontsld)
  (cond
    ((= altext_curr_style_n "0") (setq t1_font popfont))
    ((= altext_curr_style_n "1") (setq t2_font popfont))
    ((= altext_curr_style_n "2") (setq t3_font popfont))
    ((= altext_curr_style_n "3") (setq t4_font popfont))
    ((= altext_curr_style_n "4") (setq t5_font popfont))
    ((= altext_curr_style_n "5") (setq t6_font popfont))
    ((= altext_curr_style_n "6") (setq t7_font popfont))
  )  
)

;defne a fonte selecionada
(defun altext_popfont ()
  (setq popfont
	 (cond
	   ((=  "0" font_n) "0")
	   ((=  "1" font_n) "1")
	   ((=  "2" font_n) "2")
	   ((=  "3" font_n) "3")
	   ((=  "4" font_n) "4")
	   ((=  "5" font_n) "5")
	   ((=  "6" font_n) "6")
	   ((=  "7" font_n) "7")
	   ((=  "8" font_n) "8")
	   ((=  "9" font_n) "9")
	   ((=  "10" font_n) "10")
	   ((=  "11" font_n) "11")
	 )
  )
)

;atualiza o slide da fonte
(defun altext_fontsld ()
  (setq x (dimx_tile "altext_font_img") y (dimy_tile "altext_font_img"))
  (start_image "altext_font_img")
  (fill_image 0 0 x y -2)
  (end_image)
  (start_image "altext_font_img")
  (cond
    ((=  "0" font_n) (slide_image 0 0 x y (strcat cnp_root "/slides/altext_arial.sld")))
    ((=  "1" font_n) (slide_image 0 0 x y (strcat cnp_root "/slides/altext_arial_black.sld")))
    ((=  "2" font_n) (slide_image 0 0 x y (strcat cnp_root "/slides/altext_CityBlueprint.sld")))
    ((=  "3" font_n) (slide_image 0 0 x y (strcat cnp_root "/slides/altext_comic.sld")))
    ((=  "4" font_n) (slide_image 0 0 x y (strcat cnp_root "/slides/altext_Italic.sld")))
    ((=  "5" font_n) (slide_image 0 0 x y (strcat cnp_root "/slides/altext_romans.sld")))
    ((=  "6" font_n) (slide_image 0 0 x y (strcat cnp_root "/slides/altext_scriptc.sld")))
    ((=  "7" font_n) (slide_image 0 0 x y (strcat cnp_root "/slides/altext_simplex.sld")))
    ((=  "8" font_n) (slide_image 0 0 x y (strcat cnp_root "/slides/altext_times.sld")))
    ((=  "9" font_n) (slide_image 0 0 x y (strcat cnp_root "/slides/altext_verdana.sld")))
    ((=  "10" font_n) (slide_image 0 0 x y (strcat cnp_root "/slides/altext_technic.sld")))
    ((=  "11" font_n) (slide_image 0 0 x y (strcat cnp_root "/slides/altext_isocpeur.sld")))
  )
  (end_image)
)


;separa os dados de uma linha lida
(defun altext_separa_dados ()
  (setq cont1 1 n_pto "" cn7_dado1 "" cn7_dado2 "" cn7_dado3 "")
  (extrai_n)
  (setq cn7_dado1 n_pto n_pto "")
  (while (or (= (substr linha cont1 1) " " ) (= (substr linha cont1 1) "\t")(= (substr linha cont1 1) ";"))
    (setq cont1 (1+ cont1))
  );while
  (extrai_n)
  (setq cn7_dado2 n_pto n_pto "")
  (while (or (= (substr linha cont1 1) " " ) (= (substr linha cont1 1) "\t")(= (substr linha cont1 1) ";"))
    (setq cont1 (1+ cont1))
  );while
  (extrai_n)
  (setq cn7_dado3 n_pto n_pto "")
  (while (or (= (substr linha cont1 1) " " ) (= (substr linha cont1 1) "\t")(= (substr linha cont1 1) ";"))
    (setq cont1 (1+ cont1))
  );while
  (setq linha nil)
)

;salva o arquivo
(defun cn7_text_ok ()
  (setq file1 (open (strcat cnp_root "/config/altext.txt") "w" "utf8"))
  (write-line (strcat t1_font ";" t1_alt ";" t1_col) file1)
  (write-line (strcat t2_font ";" t2_alt ";" t2_col) file1)
  (write-line (strcat t3_font ";" t3_alt ";" t3_col) file1)
  (write-line (strcat t4_font ";" t4_alt ";" t4_col) file1)
  (write-line (strcat t5_font ";" t5_alt ";" t5_col) file1)
  (write-line (strcat t6_font ";" t6_alt ";" t6_col) file1)
  (write-line (strcat t7_font ";" t7_alt ";" t7_col) file1)
  (close file1)
)


;***********************************************************
;Botão "Limits"
;***********************************************************
(defun c:lim () (setq cn7_cfgmain_return 0) (cn7_cfgmain_limits) (princ))

(defun cn7_cfgmain_limits ()
  (cn7_cfg_limits_file)
  (cn7_cfg_limits)
  (if (= 1 cn7_cfgmain_return) (cn7_cfg_main))
)

;lê os dados iniciais da DCL no arquivo de dados
(defun cn7_cfg_limits_file ()
  (if (findfile (strcat cnp_root "/config/limites.txt"))
    (cn7_limits_readfile)
    (progn
      (setq file (open (strcat cnp_root "/config/limites.txt") "w" "utf8"))
      (write-line "40.00" file)
      (write-line "30.00" file)
      (write-line "0.00" file)
      (write-line "0.00" file)
      (close file)
      (cn7_limits_readfile)
    )
  )
)

;função que lê o arquivo de dados
(defun cn7_limits_readfile ()
  (setq	file (open (strcat cnp_root "/config/limites.txt") "r" "utf8")
	cn7_cfg_limits_largura	   (read-line file)
	cn7_cfg_limits_altura	   (read-line file)
	cn7_cfg_limits_x0	   (read-line file)
	cn7_cfg_limits_y0	   (read-line file)
  )
  (close file)
)


;DCL de controle dos limites a serem utilizados
(defun cn7_cfg_limits ()
;abre a dcl
  (setq dcl_id (load_dialog (strcat cnp_root "/lisp/cadnorma.dcl")))
  (if (not (new_dialog "cn7_cfg_limits" dcl_id)) (exit))
  ;preenche a DCL com os dados lidos
  ;largura
  (set_tile "cn7_cfg_limits_largura" cn7_cfg_limits_largura)
  (action_tile "cn7_cfg_limits_largura" "(cn7_lim_verilarg)")
  ;altura
  (set_tile "cn7_cfg_limits_altura" cn7_cfg_limits_altura)
  (action_tile "cn7_cfg_limits_altura" "(cn7_lim_verialt)")
  ;x0
  (set_tile "cn7_cfg_limits_x0" cn7_cfg_limits_x0)
  (action_tile "cn7_cfg_limits_x0" "(cn7_lim_verix0)")
  ;y0
  (set_tile "cn7_cfg_limits_y0" cn7_cfg_limits_y0)
  (action_tile "cn7_cfg_limits_y0" "(cn7_lim_veriy0)")
;ações dos botões
  (action_tile "cn7_cfg_limits_area" "(done_dialog 2)")
  (action_tile "cn7_cfg_limits_pick" "(done_dialog 3)")
  (action_tile "accept" "(done_dialog 1)")
  (action_tile "cancel" "(done_dialog 0)")
  (setq cn_limit_dialog (start_dialog))
  (unload_dialog dcl_id)
;o que fazer depois
  (if (= 0 cn_limit_dialog) (cn7_limit_ok))
  (if (= 1 cn_limit_dialog) (cn7_limit_ok))
  (if (= 2 cn_limit_dialog) (cn7_limits_pickarea))
  (if (= 3 cn_limit_dialog) (cn7_limits_pickpoint))
)

;botão pick_point
(defun cn7_limits_pickpoint ()
  (setq cn7_lim_pt1 (getpoint "\nEntre com o canto inferior esquerdo...")
	cn7_cfg_limits_x0 (rtos (nth 0 cn7_lim_pt1) 2 2)
	cn7_cfg_limits_y0 (rtos (nth 1 cn7_lim_pt1) 2 2)
  )
  (cn7_cfg_limits)
  (set_tile "cn7_cfg_limits_x0" cn7_cfg_limits_x0)
  (set_tile "cn7_cfg_limits_y0" cn7_cfg_limits_y0)
)
	

;botão pick area
(defun cn7_limits_pickarea ()
  (setq cn7_lim_pt1 (getpoint "\nEntre com o canto inferior esquerdo..."))
  (setq cn7_lim_pt2 (getcorner cn7_lim_pt1 "\nEntre com o canto superior direito..."))
  (setq cn7_cfg_limits_x0 (rtos (nth 0 cn7_lim_pt1) 2 2)
	cn7_cfg_limits_y0 (rtos (nth 1 cn7_lim_pt1) 2 2)
	cn7_cfg_limits_largura
	 (rtos (- (nth 0 cn7_lim_pt2) (distof cn7_cfg_limits_x0)) 2 2)
	cn7_cfg_limits_altura
	 (rtos (- (nth 1 cn7_lim_pt2) (distof cn7_cfg_limits_y0)) 2 2)
  )
  (cn7_cfg_limits)
  (set_tile "cn7_cfg_limits_largura" cn7_cfg_limits_largura)
  (set_tile "cn7_cfg_limits_altura" cn7_cfg_limits_altura)
  (set_tile "cn7_cfg_limits_x0" cn7_cfg_limits_x0)
  (set_tile "cn7_cfg_limits_y0" cn7_cfg_limits_y0)
) 



;Verifica dado Largura
(defun cn7_lim_verilarg ()
  (setq cn7_cfg_limits_largura $value)
  (if (= nil (distof cn7_cfg_limits_largura))
    (progn
      (alert "A largura deve ser um número real!\nTente novamente...")
      (mode_tile "cn7_cfg_limits_largura" 2)
    )
  )
)

;Verifica dado Altura
(defun cn7_lim_verialt ()
  (setq cn7_cfg_limits_altura $value)
  (if (= nil (distof cn7_cfg_limits_altura))
    (progn
      (alert "A altura deve ser um número real!\nTente novamente...")
      (mode_tile "cn7_cfg_limits_altura" 2)
    )
  )
)

;Verifica dado X0
(defun cn7_lim_verix0 ()
  (setq cn7_cfg_limits_x0 $value)
  (if (= nil (distof cn7_cfg_limits_x0))
    (progn
      (alert "A coordenada 'X' do ponto deve ser um número real!\nTente novamente...")
      (mode_tile "cn7_cfg_limits_x0" 2)
    )
  )
)

;Verifica dado Y0
(defun cn7_lim_veriy0 ()
  (setq cn7_cfg_limits_y0 $value)
  (if (= nil (distof cn7_cfg_limits_y0))
    (progn
      (alert "A coordenada 'Y' do ponto deve ser um número real!\nTente novamente...")
      (mode_tile "cn7_cfg_limits_y0" 2)
    )
  )
)


;função que escreve o arquivo de dados
(defun cn7_limit_ok ()
  ;escreve o arquivo
  (setq	file (open (strcat cnp_root "/config/limites.txt") "w" "utf8"))
  (write-line cn7_cfg_limits_largura file)
  (write-line	cn7_cfg_limits_altura file)
  (write-line cn7_cfg_limits_x0 file)
  (write-line cn7_cfg_limits_y0 file)
  (close file)
  (if (= 1 cn7_cfgmain_return) (cn7_cfg_main) (cn7_dwg_limits))
)


;altera o valor dos limites, de acordo com o arquivo de dados
(defun cn7_dwg_limits ()
  (cn7_limits_readfile)
  (setq pt1 (list (distof cn7_cfg_limits_x0) (distof cn7_cfg_limits_y0))
	pt2 (list
	      (+ (distof cn7_cfg_limits_x0) (distof cn7_cfg_limits_largura))
	      (+ (distof cn7_cfg_limits_y0) (distof cn7_cfg_limits_altura))
	    )
  )
  (command "._limits" "_non" pt1 "_non" pt2)
  (command "._zoom" "_non" pt1 "_non" pt2 "._zoom" ".9x")
)


;***********************************************************
;Botão OK - CARBURADOR
;***********************************************************
(defun cn7_cfgmain_ok ()
  (cnp:require-vars '("REGENMODE" "DIMLUNIT" "DIMSHO" "DIMASSOC"))
  (setvar "regenmode" 0)
  (setvar "cmdecho" 0)
  (setvar "mirrtext" 0)
  (cn7_cfgmain_savecfg)
  ;define a unidade de desenho  
  (cond
    ((= cfgdata_dwgunit "0") (setq cn7_dwgunit 1.0) (setvar "userr5" 1.0));metros
    ((= cfgdata_dwgunit "1") (setq cn7_dwgunit 100.0) (setvar "userr5" 100.0));centimetros
    ((= cfgdata_dwgunit "2") (setq cn7_dwgunit 1000.0) (setvar "userr5" 1000.0));milimetros
  )
  ;define a unidade de cota 
  (cond
    ((= cfgdata_dimunit "0") (setq cn7_dimunit 1.0)  (setvar "userr4" 1.0));m
    ((= cfgdata_dimunit "1") (setq cn7_dimunit 100.0)  (setq cn7_dimunit 100.0) (setvar "userr4" 100.0));cm
    ((= cfgdata_dimunit "2") (setq cn7_dimunit 1000.0) (setvar "userr4" 1000.0));mm
  )
  ;configuração de espaço
  (setvar "useri3" (fix (distof cfgdata_app_space)))
  ;configurações de texto
  (cn7_config_text)
  (cn7_dwg_altext)
  ;configurações de cotas
  (cn7_dwg_dim)
  (cn7_dwg_aldim)
  ;configurações de layers
  (cn7_dwg_allayer)
  ;configurações de limites (se clicado)
  (if (= cfgdata_app_limits "1") (cn7_dwg_limits))
  ;solicita escala para o model space
  (cn7_esc)
  (command "._dimstyle" "_restore" "cadnorma_dim1")
  (command "._regen")
)



;******************************************************************************
;******************************************************************************
;Configurações de texto
;******************************************************************************
;******************************************************************************

;textos padrão cadnorma
(defun cn7_config_text ()
  ;fonte Romans
  (command "._style" "r50"  "romans" "0" "" "" "" "" "")
  (command "._style" "r60"  "romans" "0" "" "" "" "" "")
  (command "._style" "r70"  "romans" "0" "" "" "" "" "")
  (command "._style" "r80"  "romans" "0" "" "" "" "" "")
  (command "._style" "r90"  "romans" "0" "" "" "" "" "")
  (command "._style" "r100" "romans" "0" "" "" "" "" "")
  (command "._style" "r120" "romans" "0" "" "" "" "" "")
  (command "._style" "r140" "romans" "0" "" "" "" "" "")
  (command "._style" "r175" "romans" "0" "" "" "" "" "")
  (command "._style" "r200" "romans" "0" "" "" "" "" "")
  (setvar "regenmode" 1)
  (setvar "textstyle" "r80")
)

;textos padrão do usuário
(defun cn7_dwg_altext ()
  (setq font_list (list "arial.ttf" "ariblk.ttf" "cityb___.ttf"
			"comic.ttf" "italic.shx" "romans.shx"
			"scriptc.shx" "simplex.shx" "times.ttf"
			"verdana.ttf" "technic_.ttf" "isocpeur.ttf"))
  (cn7_cfg_altext_file)
  ;t1
  (setq font (nth (fix (distof t1_font)) font_list))  
  (command "._style" "T1" font "0" "" "" "" "")
  (if (or (= t1_font "4") (= t1_font "5") (= t1_font "6") (= t1_font "7")) (command ""))
  ;t2
  (setq font (nth (fix (distof t2_font)) font_list))  
  (command "._style" "T2" font "0" "" "" "" "")
  (if (or (= t2_font "4") (= t2_font "5") (= t2_font "6") (= t2_font "7")) (command ""))
  ;t3
  (setq font (nth (fix (distof t3_font)) font_list))  
  (command "._style" "T3" font "0" "" "" "" "")
  (if (or (= t3_font "4") (= t3_font "5") (= t3_font "6") (= t3_font "7")) (command ""))
  ;t4
  (setq font (nth (fix (distof t4_font)) font_list))  
  (command "._style" "T4" font "0" "" "" "" "")
  (if (or (= t4_font "4") (= t4_font "5") (= t4_font "6") (= t4_font "7")) (command ""))
  ;t5
  (setq font (nth (fix (distof t5_font)) font_list))  
  (command "._style" "T5" font "0" "" "" "" "")
  (if (or (= t5_font "4") (= t5_font "5") (= t5_font "6") (= t5_font "7")) (command ""))
  ;t6
  (setq font (nth (fix (distof t6_font)) font_list))  
  (command "._style" "T6" font "0" "" "" "" "")
  (if (or (= t6_font "4") (= t6_font "5") (= t6_font "6") (= t6_font "7")) (command ""))
  ;t7
  (setq font (nth (fix (distof t7_font)) font_list))  
  (command "._style" "T7" font "0" "" "" "" "")
  (if (or (= t7_font "4") (= t7_font "5") (= t7_font "6") (= t7_font "7")) (command ""))
)


;******************************************************************************
;******************************************************************************
;Configurações de cotas (dimension)
;******************************************************************************
;******************************************************************************

(defun cn7_dwg_dim ()
  (cn7_cfg_dim1);cria cadnorma_dim1 & cadnorma_dim2
  (cn7_cfg_dim2);cria cadnorma_dim3
)

(defun cn7_cfg_dim1 ()
  (if (tblsearch "dimstyle" "cadnorma_dim1")
    (command "._dimstyle" "_r" "cadnorma_dim1")
  )
  ;decide o tipo de bloco usado na cota
  (setvar "dimtsz" 0)
  (setvar "dimsah" 0)
  (setvar "dimblk" "_archtick")
  (setvar "dimblk1" "_archtick")
  (setvar "dimblk2" "_archtick")
  (setvar "dimldrblk" ".")
  (setvar "dimasz" 1.2)
  ;diferenciado da apresentação
  (setvar "DIMSD1" 0)
  (setvar "DIMSD2" 0)
  (setvar "DIMJUST" 0)
  ;dimlfac para unidade de cota / unidade do desenho
  (setvar "dimlfac"  (/ cn7_dimunit cn7_dwgunit))
  ;dimdsep -> separador de decimais
  (setvar "dimdsep" ".")
  ;cores da cota
  (setvar "dimclrd" 1)
  (setvar "dimclre" 1)
  (setvar "dimclrt" 2)
  ;******** Configuraçòes comuns ************
  (setvar "dimatfit" 	0)
  (setvar "dimalt" 	0)
  (setvar "dimaltd"   	2)
  (setvar "dimlunit" 2)
  (setvar "dimaltf"   	25.4)
  (setvar "dimpost" 	"")
  ;(setvar "dimassoc" 	1)
  (setvar "dimcen" 	-1)
  (setvar "dimdle" 	1)
  (setvar "dimdli" 	5.0)
  (setvar "dimexe"    	1)
  (setvar "dimexo"    	2.5)
  (setvar "dimgap"    	0.60)
  (setvar "dimlim"    	0)
  (setvar "dimrnd"    	0.0)
  (setvar "dimse1"    	0)
  (setvar "dimse2"    	0)
  (setvar "dimsho"    	1)
  (setvar "dimsoxd"   	0)
  (setvar "dimtad"    	1)
  (setvar "dimtfac"   	1)
  (setvar "dimtih"    	0)
  (setvar "dimtix"    	1)
  (setvar "dimtm" 	0.0)
  (setvar "dimtofl"   	1)
  (setvar "dimtoh"    	0)
  (setvar "dimtol"    	0)
  (setvar "dimtp" 	0.0)
  (setvar "dimaunit" 	1)
  (setvar "dimadec" 	2)
  (cond
    ((= cn7_dimunit 1.0) (setvar "dimdec" 2) (setvar "dimzin" 4))
    ((= cn7_dimunit 100.0) (setvar "dimdec" 1) (setvar "dimzin" 8))
    ((= cn7_dimunit 1000.0) (setvar "dimdec" 1) (setvar "dimzin" 8))
  )
  (setvar "dimtxt" 2.0)
  (setvar "dimtmove" 2)
  (setvar "dimtxsty" "r80")
  (setvar "dimscale" 0) 
  (if (tblsearch "dimstyle" "cadnorma_dim1")
    (command "._dimstyle" "_s" "cadnorma_dim1" "_y")
    (command "._dimstyle" "_s" "cadnorma_dim1")
  )
  (setvar "dimblk" ".")
  (setvar "dimblk1" ".")
  (setvar "dimblk2" ".")
  (setvar "dimasz" 1.5)
  (if (tblsearch "dimstyle" "cadnorma_dim2")
    (command "._dimstyle" "_s" "cadnorma_dim2" "_y")
    (command "._dimstyle" "_s" "cadnorma_dim2")
  )
)

;cota para apresentação
(defun cn7_cfg_dim2 ()
  (setvar "DIMALTTD" 2)
  (setvar "DIMBLK" "_none")
  (setvar "DIMSD1" 1)
  (setvar "DIMSD2" 1)
  (setvar "DIMSE1" 1)
  (setvar "DIMSE2" 1)
  (setvar "dimclrt" 256)
  (setvar "dimjust" 1)
  (setvar "dimtxsty" "r80")
  (if (tblsearch "dimstyle" "cadnorma_dim3")
    (command "._dimstyle" "_s" "cadnorma_dim3" "_y")
    (command "._dimstyle" "_s" "cadnorma_dim3")
  )
)


;configuração de cotas custom
(defun cn7_dwg_aldim ()
  (command "._dimstyle" "_r" "cadnorma_dim1")
  ;coleta os parâmetros de configuração no arquivo de dados
  (cn7_cfg_aldim_file)
  ;habilita movimentação dos textos
  (setvar "dimtmove" 2)
  ;decide o tipo de bloco usado na cota
  (setvar "dimblk1" ".")
  (setvar "dimblk2" ".")
  (cond
    ((= aldim_blk1 "0") (setvar "dimblk" "_archtick") (setvar "dimtsz" 0) (setvar "dimasz" 1.2))
    ((= aldim_blk1 "1") (setvar "dimblk" "_dot") (setvar "dimtsz" 0) (setvar "dimasz" 1.0))
    ((= aldim_blk1 "2") (setvar "dimblk" "_open30") (setvar "dimtsz" 0) (setvar "dimasz" 1.2))
    ((= aldim_blk1 "3") (setvar "dimblk" "_open90") (setvar "dimtsz" 0) (setvar "dimasz" 1.2))
    ((= aldim_blk1 "4") (setvar "dimblk" ".") (setvar "dimtsz" 0) (setvar "dimasz" 1.2))
    ((= aldim_blk1 "5") (setvar "dimblk" ".") (setvar "dimtsz" 0.6) (setvar "dimasz" 1.2))
  )
  ;dimlfac para unidade de cota / unidade do desenho
  (setvar "dimlfac"  (/ cn7_dimunit cn7_dwgunit))
  ;dimdsep -> separador de decimais
  (if (= aldim_dsep "0") (setvar "dimdsep" ".") (setvar "dimdsep" ","))
  ;define as cores da cota
  (setvar "dimclrd" 	(fix (distof aldim_dcol)))
  (setvar "dimclre" 	(fix (distof aldim_dcol)))
  (setvar "dimclrt" 	(fix (distof aldim_tcol)))
  ;definição de casas decimais
  (setvar "dimdec" (fix (distof aldim_ddec)))
  ;supressão de zeros
  ;*****************************************************
  (cond
    ((= aldim_dzin "0") (setvar "dimzin" 4))
    ((= aldim_dzin "1") (setvar "dimzin" 8))
    ((= aldim_dzin "2") (setvar "dimzin" 12))
    ((= aldim_dzin "3") (setvar "dimzin" 0))
  )

  ;estilo selecionado
  (setq aldim_stylist (list "r50" "r60" "r70" "r80" "r90" "r100" "r120" "r140" "r175" "r200"
			    "t1" "t2" "t3" "t4" "t5" "t6" "t7"))
  (setvar "dimtxsty" (nth (fix (distof aldim_txst)) aldim_stylist))
  ;define a altura do texto
  (cond
    ((= (strcase (getvar "dimtxsty") t) "r50") (setvar "dimtxt" hf_r50))
    ((= (strcase (getvar "dimtxsty") t) "r60") (setvar "dimtxt" hf_r60))
    ((= (strcase (getvar "dimtxsty") t) "r70") (setvar "dimtxt" hf_r70))
    ((= (strcase (getvar "dimtxsty") t) "r80") (setvar "dimtxt" hf_r80))
    ((= (strcase (getvar "dimtxsty") t) "r90") (setvar "dimtxt" hf_r90))
    ((= (strcase (getvar "dimtxsty") t) "r100") (setvar "dimtxt" hf_r100))
    ((= (strcase (getvar "dimtxsty") t) "r120") (setvar "dimtxt" hf_r120))
    ((= (strcase (getvar "dimtxsty") t) "r140") (setvar "dimtxt" hf_r140))
    ((= (strcase (getvar "dimtxsty") t) "r175") (setvar "dimtxt" hf_r175))
    ((= (strcase (getvar "dimtxsty") t) "r200") (setvar "dimtxt" hf_r200))
    ((= (strcase (getvar "dimtxsty") t) "t1") (cn7_cfg_altext_file) (setvar "dimtxt" (distof t1_alt)))
    ((= (strcase (getvar "dimtxsty") t) "t2") (cn7_cfg_altext_file) (setvar "dimtxt" (distof t2_alt)))
    ((= (strcase (getvar "dimtxsty") t) "t3") (cn7_cfg_altext_file) (setvar "dimtxt" (distof t3_alt)))
    ((= (strcase (getvar "dimtxsty") t) "t4") (cn7_cfg_altext_file) (setvar "dimtxt" (distof t4_alt)))
    ((= (strcase (getvar "dimtxsty") t) "t5") (cn7_cfg_altext_file) (setvar "dimtxt" (distof t5_alt)))
    ((= (strcase (getvar "dimtxsty") t) "t6") (cn7_cfg_altext_file) (setvar "dimtxt" (distof t6_alt)))
    ((= (strcase (getvar "dimtxsty") t) "t7") (cn7_cfg_altext_file) (setvar "dimtxt" (distof t7_alt)))
    (t (setvar "dimtxt" 2.0))
  )
  (setvar "dimscale" 0) 
  (if (tblsearch "dimstyle" "cadnorma_dim4")
    (command "._dimstyle" "_s" "cadnorma_dim4" "_y")
    (command "._dimstyle" "_s" "cadnorma_dim4")
  )
  (cond
    ((= aldim_blk2 "0") (setvar "dimblk" "_archtick") (setvar "dimtsz" 0) (setvar "dimasz" 1.2))
    ((= aldim_blk2 "1") (setvar "dimblk" "_dot") (setvar "dimtsz" 0) (setvar "dimasz" 1.0))
    ((= aldim_blk2 "2") (setvar "dimblk" "_open30") (setvar "dimtsz" 0) (setvar "dimasz" 1.2))
    ((= aldim_blk2 "3") (setvar "dimblk" "_open90") (setvar "dimtsz" 0) (setvar "dimasz" 1.2))
    ((= aldim_blk2 "4") (setvar "dimblk" ".") (setvar "dimtsz" 0) (setvar "dimasz" 1.2))
    ((= aldim_blk2 "5") (setvar "dimblk" ".") (setvar "dimtsz" 0.6))
  )
  (setvar "dimldrblk" (getvar "dimblk"))
  ;dimleader em dot (variar para a próxima versão)
  (if (tblsearch "dimstyle" "cadnorma_dim5")
    (command "._dimstyle" "_s" "cadnorma_dim5" "_y")
    (command "._dimstyle" "_s" "cadnorma_dim5")
  )
)

;*********************************************************************
;funções de erro
;*********************************************************************
(defun guarda (VS / VI value)
  (setq err_temp *ERROR*)
  (setq *error* armadilha)
  (setq restlist '())
   (while VS
      (setq VI (car VS)
            value (getvar VI)
            restlist (append restlist (list (list VI value)))
            VS (cdr VS)
      )
   )
)

(defun devolve ()  
  (setq *error* err_temp)
  (while restlist
     (setq VI (car (car restlist))
           value (car (cdr (car restlist)))
     )
     (setvar VI value)
     (setq restlist (cdr restlist))
  )
)


(defun armadilha (errmsg) 
  (command nil nil nil)
  (if (not
	(member errmsg
	   '("console break" "Function Cancelled"))
      )
    (princ (strcat "\nError: " errmsg))
)
(princ)
(terpri)
(setq *error* err_temp)
(princ)
)

;*********************************************************************
;função que encontra a escala da janela
;*********************************************************************
(defun cn7_vport_scl ()
  (setq cn7_ddzin (getvar "dimzin"))
  (setvar "dimzin" 1)
  (if (not (and (= 0 (getvar "tilemode")) (= 1 (getvar "cvport"))))
    (setq scl_list (assoc (getvar "cvport") (setq all_views (vports)))
	  scl_delta (-  (nth 1 (nth 2 scl_list)) (nth 1 (nth 1 scl_list)))
	  cn7_vp_scale (/ (* 1000 (/ (getvar "viewsize") scl_delta)) cn7_dwgunit);next->
    )
    (alert "não está na janela")
  )
  (setvar "dimzin" cn7_ddzin)
  (setq cn10_vp_scale (* 1000 (/ (getvar "viewsize") scl_delta)))
)

;***********************************************************************
;verifica se a escala da janela é válida -> retorna: cn7_msscl -> userr3
;***********************************************************************
(defun cn7_veryscale ()
  (setq cn7_dzin (getvar "dimzin"))
  (setvar "dimzin" 1)
  (cn7_vport_scl)
  (setq cn7_listmemb "n" alert_resp nil)
  (setq cn7_scalist
	 (list
	   "1.000" "10.000" "100.000" "1000.000" "10000.000" "100000.000" "1000000.000"
	   "1.250" "12.500" "125.000" "1250.000" "12500.000" "125000.000"
	   "1.500" "15.000" "150.000" "1500.000" "15000.000" "150000.000"
	   "2.000" "20.000" "200.000" "2000.000" "20000.000" "200000.000"
	   "2.500" "25.000" "250.000" "2500.000" "25000.000" "250000.000"
	   "3.000" "30.000" "300.000" "3000.000" "30000.000" "300000.000"
	   "4.000" "40.000" "400.000" "4000.000" "40000.000" "400000.000"
	   "5.000" "50.000" "500.000" "5000.000" "50000.000" "500000.000"
	   "7.500" "75.000" "750.000" "7500.000" "75000.000" "750000.000"))
  ;next->
  (setq cn7_vpscl_verify cn7_vp_scale)
  (foreach n cn7_scalist
    (if (= (rtos cn7_vpscl_verify 2 3) n) (setq cn7_listmemb "s"))
  )
  (setvar "dimzin" cn7_dzin)
  (if (= cn7_listmemb "n")
    ;se a escala da janela é irregular
    (progn
      (cn7_alert_yes_no
	"A escala dessa Viewport não é padrão!"
	(strcat "Escala atual = 1:" (rtos cn7_vpscl_verify 2 3))
	"Deseja continuar mesmo assim?")
      (if (= "no" alert_resp)
	(exit)
	(progn
	  (setq cn7_msscl cn7_vp_scale)
	  (setvar "userr3" cn7_msscl)
	)
      )
    );
    ;se a escala da janela é regular
    (progn
      (setq cn7_msscl cn7_vp_scale)
      (setvar "userr3" cn7_msscl)
    )
  );if
  (princ)
)



;*********************************************************************
;  Mensagens de Alerta com DCL`s personalizadas **********************
;*********************************************************************

;somente com o botão "ok"
(defun cn7_alert_ok (msg1 msg2 msg3)
  (setq alert_resp nil)
  (setq dcl_id (load_dialog (strcat cnp_root "/lisp/cadnorma.dcl")))
  (if (not (new_dialog "cn7_msg_ok" dcl_id)) (exit))
  (set_tile "msg_text1" msg1)
  (set_tile "msg_text2" msg2)
  (set_tile "msg_text3" msg3)
  (action_tile "accept" " (done_dialog 1)")
  (setq msg_resp (start_dialog))
  (unload_dialog dcl_id)
  (princ)
)

;com os botões "ok" e "cancel"
(defun cn7_alert_ok_cancel (msg1 msg2 msg3)
  (setq alert_resp nil)
  (setq dcl_id (load_dialog (strcat cnp_root "/lisp/cadnorma.dcl")))
  (if (not (new_dialog "cn7_msg_ok_cancel" dcl_id)) (exit))
  (set_tile "msg_text1" msg1)
  (set_tile "msg_text2" msg2)
  (set_tile "msg_text3" msg3)
  (action_tile "accept" " (done_dialog 1)")
  (setq msg_resp (start_dialog))
  (unload_dialog dcl_id)
  (if (= msg_resp 1) (setq alert_resp "ok") (setq alert_resp "cancel"))
  (princ)
)


;com os botões "Sim", "Não"
(defun cn7_alert_yes_no (msg1 msg2 msg3)
  (setq alert_resp nil)
  (setq dcl_id (load_dialog (strcat cnp_root "/lisp/cadnorma.dcl")))
  (if (not (new_dialog "cn7_msg_yes_no" dcl_id)) (exit))
  (set_tile "msg_text1" msg1)
  (set_tile "msg_text2" msg2)
  (set_tile "msg_text3" msg3)
  (action_tile "yes" " (done_dialog 1)")
  (setq msg_resp (start_dialog))
  (unload_dialog dcl_id)
  (if (= msg_resp 1) (setq alert_resp "yes") (setq alert_resp "no"))
  (princ)
)

;com os botões "Sim", "Não" e Cancela
(defun cn7_alert_yes_no_cancel (msg1 msg2 msg3)
  (setq alert_resp nil)
  (setq dcl_id (load_dialog (strcat cnp_root "/lisp/cadnorma.dcl")))
  (if (not (new_dialog "cn7_msg_yes_no_cancel" dcl_id)) (exit))
  (set_tile "msg_text1" msg1)
  (set_tile "msg_text2" msg2)
  (set_tile "msg_text3" msg3)
  (action_tile "yes" "(done_dialog 1)")
  (action_tile "no" "(done_dialog 2)")
  (setq msg_resp (start_dialog))
  (unload_dialog dcl_id)
  (if (= msg_resp 1)
    (setq alert_resp "yes")
    (progn
      (if (= msg_resp 2)
	(setq alert_resp "no")
	(setq alert_resp "cancel")
      )
    )
  )
  (princ)
)

;*********************************************************************
;pergunta a configuração
;*********************************************************************
(defun c:?cfg ()
  (cn7_init)
  (setq cn7_dzin (getvar "dimzin"))
  (setvar "dimzin" 1)
  (if (= 0 (getvar "tilemode"))
    (if (= 1 (getvar "cvport"))
      (setq msg5 "Operando no Paper Space")
      (progn
	(cn7_vport_scl)
	(cond
	  ((= cn7_dwgunit 1000.0) (setq msg5_scale cn7_vp_scale))
	  ((= cn7_dwgunit 100.0) (setq msg5_scale cn7_vp_scale))
	  ((= cn7_dwgunit 1.0) (setq msg5_scale cn7_vp_scale))
	  )
	(setq msg5 (strcat "Escala da Viewport = 1:" (rtos msg5_scale 2 2)))
	)
    )
    (if cn7_msscl
      (setq msg5 (strcat "Model Space, escala 1: " (rtos cn7_msscl 2 0)))
      (setq msg5 "Desenho não configurado!")
    )
  )
  (cond
    ((= "1.00" (rtos cn7_dwgunit 2 2))  (setq msg3 "Desenhando em : metros..."))
    ((= "100.00" (rtos cn7_dwgunit 2 2))  (setq msg3 "Desenhando em : centímetros..."))
    ((= "1000.00" (rtos cn7_dwgunit 2 2))  (setq msg3 "Desenhando em : milímetros..."))
  )
  (cond
    ((= "1.00" (rtos cn7_dimunit 2 2))  (setq msg4 "Cotando em : metros..."))
    ((= "100.00" (rtos cn7_dimunit 2 2))  (setq msg4 "Cotando em : centímetros..."))
    ((= "1000.00" (rtos cn7_dimunit 2 2))  (setq msg4 "Cotando em : milímetros..."))
  )
  (setq dcl_id (load_dialog (strcat cnp_root "/lisp/cadnorma.dcl")))
  (if (not (new_dialog "cn7_msg_cfg" dcl_id)) (exit))
  (set_tile "msg_text3" msg3)
  (set_tile "msg_text4" msg4)
  (set_tile "msg_text5" msg5)
  (action_tile "accept" " (done_dialog 1)")
  (setq msg_resp (start_dialog))
  (unload_dialog dcl_id)
  (setvar "dimzin" cn7_dzin)
  (princ)
)
;*********************************************************************
;determina a altura final dos textos
;*********************************************************************
(defun cn7_text_hfinal ()
  (cond
    ;case romans
    ((= (strcase cn7_txtsty t) "r50") (setq cn7_txthf 1.25))
    ((= (strcase cn7_txtsty t) "r60") (setq cn7_txthf 1.50))
    ((= (strcase cn7_txtsty t) "r70") (setq cn7_txthf 1.75))
    ((= (strcase cn7_txtsty t) "r80") (setq cn7_txthf 2.00))
    ((= (strcase cn7_txtsty t) "r90") (setq cn7_txthf 2.25))
    ((= (strcase cn7_txtsty t) "r100") (setq cn7_txthf 2.50))
    ((= (strcase cn7_txtsty t) "r120") (setq cn7_txthf 3.00))
    ((= (strcase cn7_txtsty t) "r140") (setq cn7_txthf 3.50))
    ((= (strcase cn7_txtsty t) "r175") (setq cn7_txthf 4.375))
    ((= (strcase cn7_txtsty t) "r200") (setq cn7_txthf 5.0))
    ((= (strcase cn7_txtsty t) "t1") (setq cn7_txthf (distof t1_alt)))
    ((= (strcase cn7_txtsty t) "t2") (setq cn7_txthf (distof t2_alt)))
    ((= (strcase cn7_txtsty t) "t3") (setq cn7_txthf (distof t3_alt)))
    ((= (strcase cn7_txtsty t) "t4") (setq cn7_txthf (distof t4_alt)))
    ((= (strcase cn7_txtsty t) "t5") (setq cn7_txthf (distof t5_alt)))
    ((= (strcase cn7_txtsty t) "t6") (setq cn7_txthf (distof t6_alt)))
    ((= (strcase cn7_txtsty t) "t7") (setq cn7_txthf (distof t7_alt)))
  )
)
;*********************************************************************
;next-> encontra o cn7_prefixlay
;*********************************************************************
(defun cn7_find_layerprefix ()
  (if (= 1 (getvar "tilemode"))
    (setq cn7_prefixlay (strcat (rtos cn7_msscl 2 0) "-"))
    (progn
      (if (= 1 (getvar "cvport"))
	(setq cn7_prefixlay "");paper
	(progn
	  (cn7_vport_scl)
	  (setq cn7_msscl cn7_vp_scale)
	  (setq cn7_prefixlay (strcat (rtos cn7_msscl 2 0) "-"))
	)
      );if
    );progn case F
  )
)
;*********************************************************************
;função que descobre a altura dos textos e prefixo de escala
;*********************************************************************
(defun cn7_text_height ()
  (if (= 1 (getvar "tilemode"))
    (progn       ;escrever no Model Space
      (if (= nil cn7_msscl) (cn7_esc))
      (prompt (strcat "\nEscala Atual = 1:" (rtos cn7_msscl 2 0)))
      (cond
	((= cn7_dwgunit 1) (setq cn7_txth (/ (* cn7_txthf cn7_msscl) 1000.0)))
	((= cn7_dwgunit 100) (setq cn7_txth (/ (* cn7_txthf cn7_msscl) 10.0)))
	((= cn7_dwgunit 1000) (setq cn7_txth (/ (* cn7_txthf cn7_msscl) 1.0)))
      )
      (setq cn7_prefixlay (strcat (rtos cn7_msscl 2 0) "-"))
    )
    (progn
      (if (= 1 (getvar "cvport"))
	(progn   ;escrever no Paper Space
	  (prompt "\nVocê está no Paper Space...")
	  (setq cn7_txth cn7_txthf)
	  (setq cn7_prefixlay "")
	  )
	(progn    ;escrever na Janela
	  (cn7_veryscale)
	  (cond
	    ((= cn7_dwgunit 1) (setq cn7_txth (/ (* cn7_txthf cn7_msscl) 1000.0)))
	    ((= cn7_dwgunit 100) (setq cn7_txth (/ (* cn7_txthf cn7_msscl) 10.0)))
	    ((= cn7_dwgunit 1000) (setq cn7_txth (/ (* cn7_txthf cn7_msscl) 1.0)))
	  )
	  (prompt (strcat "\nViewport -> Escala 1:" (rtos cn7_msscl 2 0)))
	  (setq cn7_prefixlay (strcat (rtos cn7_msscl 2 0) "-"))
	)
      );if
    );progn case F
  )
  (princ)
)

;*********************************************************************
;mostra escala atual
;*********************************************************************
(defun c:vsc ()
  (if (= (getvar "tilemode") 0)		; se está no layout
    (progn
      (if (= (getvar "cvport") 1)	;se está no paper
	(alert "Paper Space!\nEscala 1:1 (mm)")
	(progn				;se está na viewport
	  (cn7_vport_scl)
	  (alert (strcat "Escala da Viewport = 1: " (rtos cn7_vp_scale 2 0)))
	)
     )
      )
   (alert (strcat "Escala do Model = 1: "(rtos cn7_msscl 2 0))) ;se está no Model
  )
  (princ)
)

;*********************************************************************
;alterar o fator de escala de cotas - dimlfac
;*********************************************************************
(defun c:scdim ()
  (cn7_scdim)
  (princ)
)

(defun cn7_scdim ()
  (if (/= 1 (getvar "tilemode"))
    (progn
      (alert "Esta operação só é permitida\nno Model Space")
      (exit)
    )
  )
  (setq cn7_get_msscl nil)
  (setq dcl_id (load_dialog (strcat cnp_root "/lisp/cadnorma.dcl")))
  (if (not (new_dialog "cn7_dimlfac" dcl_id)) (exit))
  
  (set_tile "cn7_dimlfac_esc_atual" (strcat "Escala do Model = " (rtos cn7_msscl 2 2)))
  (mode_tile "cn7_dimlfac_esc_nova" 2)
  (action_tile "cn7_dimlfac_esc_nova" "(scdim_dimscale)")
  (setq cn7_scdim_resp (start_dialog))
  (unload_dialog dcl_id)
  (if (= 1 cn7_scdim_resp)
    (setq scdim_newscale (/ (distof scdim_getscale) cn7_msscl ))
  )
)

(defun scdim_dimscale ()
  (setq scdim_getscale $value)
  (if (not (distof scdim_getscale))
    (progn
      (alert "Valor inválido!\nDigite um número Real.")
      (set_tile "cn7_dimlfac_esc_nova" "")
      (mode_tile "cn7_dimlfac_esc_nova" 2)
    )
  )
)
 
;*********************************************************************
;*********************************************************************
;comando de teclado para alterar escala corrente
;*********************************************************************
;*********************************************************************
(defun c:esc ()
  (cn7_esc)
  (princ)
)

;lê o arquivo com a última escala utilizada para desenhos novos
;e escalas não definidas
(defun cn7_esc_file ()
  (if (not (findfile (strcat cnp_root "/config/esc_last.txt")))
    (progn
      (setq open_file (open (strcat cnp_root "/config/esc_last.txt") "w" "utf8"))
      (write-line "100" open_file)
    )
  )
  (setq open_file (open (strcat cnp_root "/config/esc_last.txt") "r" "utf8")
	cn7_get_msscl (read-line open_file)
  )
  (close open_file)
  (if (= nil cn7_get_msscl)
    (setq cn7_get_msscl "50.00"
	  cn7_msscl (distof cn7_get_msscl)
    )
  )
  (if (distof cn7_get_msscl)
    (setq cn7_msscl (distof cn7_get_msscl))
    (progn
      (setq cn7_msscl 50.00
	    cn7_get_msscl "50.00"
      )
    )
  )
  (setvar "userr3" cn7_msscl)
  (setq cn7_prefixlay (strcat (rtos cn7_msscl 2 0) "-"))
)

;Mostra e/ou altera a escala do model
(defun cn7_esc ()
  (setq cn7_get_msscl nil)
  (if (= 0 (getvar "tilemode"));(and (= 0 (getvar "tilemode")) (= (getvar "cvport") 1))
    (progn
      (alert "Esta operação só é permitida\nno Model Space!")
      (exit)
    )
  )
  (setq dcl_id (load_dialog (strcat cnp_root "/lisp/cadnorma.dcl")))
  (if (not (new_dialog "cn7_defesc" dcl_id)) (exit))
  (if (or (= 0.0 cn7_msscl) (= nil cn7_msscl))
    (cn7_esc_file)    
  )
  (set_tile "cn7_defesc_esc_atual" (strcat "Escala Atual = 1: " (rtos cn7_msscl 2 2)))
  (set_tile "cn7_defesc_esc_nova" (rtos cn7_msscl 2 2))
  (mode_tile "cn7_defesc_esc_nova" 2)
  (action_tile "cn7_defesc_esc_nova" "(cn7_defesc_veryget)")
  (action_tile "cancel" "(done_dialog 0)")
  (action_tile "accept" "(done_dialog 1)")
  (setq cn7_esc_resp (start_dialog))
  (unload_dialog dcl_id)
  (if (= 1 cn7_esc_resp)
    (if (/= nil cn7_get_msscl)
      (progn
	(setq cn7_msscl (distof cn7_get_msscl))
	(setvar "userr3" cn7_msscl)
	(setq cn7_prefixlay (strcat (rtos cn7_msscl 2 0) "-"))
	(if (= (getvar "useri3") 1)
	  (setvar "ltscale" 10.0)
	  (setvar "ltscale" (/ (* (getvar "userr5") cn7_msscl) 100.0))
	)
	(setq open_file (open (strcat cnp_root "/config/esc_last.txt") "w" "utf8"))
	(write-line cn7_get_msscl open_file)
      )
      (progn
	(alert "Nenhuma escala escolhida!\nTente novamente...")
	(cn7_esc)
      )
    )
  )
  (princ)
)

;verifica se a entrada é válida
(defun cn7_defesc_veryget ()
  (setq cn7_get_msscl $value
	esc_complist (list))
  (if (not (distof cn7_get_msscl))
    (progn
      (cn7_alert_ok
	    "Entrada Inválida!"
	    "Digite um valor"
	    "Numérico...")
      (done_dialog 0)
    )
    (progn
      (setq cn7_dzin (getvar "dimzin"))
      (setvar "dimzin" 1)
      (setq cn7_listmemb "n" alert_resp nil)
      (foreach n reg_scale_list
	(setq esc_complist (append (list (rtos (distof n) 2 3)) esc_complist))
      )
      (setq cn7_vpscl_verify (distof cn7_get_msscl))
      (foreach n esc_complist
	(if (= (rtos cn7_vpscl_verify 2 3) n) (setq cn7_listmemb "s"))
      )
      (if (= cn7_listmemb "n")
	;se a escala da janela é irregular
	(progn
	  (cn7_alert_yes_no
	    "Esta escala não é padrão!"
	    (strcat "Escala atual = 1:" cn7_get_msscl)
	    "Deseja continuar mesmo assim?")
	  (if (= "no" alert_resp)
	    (cn7_esc)
	    (progn
	      (setq cn7_msscl (distof cn7_get_msscl))
	      (setvar "userr3" cn7_msscl)
	      (done_dialog 3)
	    )
	  )
	);
	;se a escala da janela é regular
	(progn
	  (setq cn7_msscl (distof cn7_get_msscl))
	  (setvar "userr3" cn7_msscl)
        )
      )
    )
  )
)

;*********************************************************************
;*********************************************************************
;encontra a escala dos blocos para inserção, conforme seja tipo gráfico ou real
;*********************************************************************
;*********************************************************************
(defun cn7_find_blkscl ()
  (if (= "1" grp_type)
    ;blocos do tipo Real obedecem sempre à mesma regra...
    ;se está no Paper Space, dá o ALERTA!
    (if (and (= 0 (getvar "tilemode")) (= 1 (getvar "cvport")))
      (progn	(cn7_alert_yes_no
	  "Os blocos do tipo 'Real' não"
	  "devem ser inseridos no Paper Space!"
	  "Deseja prosseguir mesmo assim?")
	(if (= alert_resp "yes")
	  (progn
	    (setq cn7_blkscl 1)
	    (setq cn7_blk_prefixlay "")
	  )
	  (progn
	    (alert "Ative uma Viewport e tente novamente!")
	    (exit)
	  )
	)
      )
      (progn
	(setq cn7_blkscl (/ cn7_dwgunit (distof grp_unit)))
	(setq cn7_blk_prefixlay "")
      )
    )
    ;blocos do tipo Gráfico variam...
    (progn
      (if (= (getvar "tilemode") 1) ;status atual = model pleno
	(progn
	  (prompt (strcat "\nEscala Atual = 1:" (rtos cn7_msscl 2 0)))
	  (setq cn7_blk_prefixlay (strcat (rtos cn7_msscl 2 0) "-"))
	  (setq cn7_blkscl (/ (* cn7_msscl cn7_dwgunit) 100.0))
	  )
	(if (= 1 (getvar "cvport")) ;se está no paper space, a escala é sempre 10 (testar!!!)
	  (progn
	    (setq cn7_blkscl 10.0)
	    (setq cn7_blk_prefixlay "")
	  )
	  (progn                    ; se está na viewport
	    (cn7_veryscale)
	    (setq cn7_blk_prefixlay (strcat (rtos cn7_msscl 2 0) "-"))
	    (setq cn7_blkscl (/ (* cn7_dwgunit cn7_msscl) 100.0))
	    )
	  )
	)
      );progn
    )
  (princ)
)

;*********************************************************************
;função que escreve textos em ferramentas e símbolos
;*********************************************************************
(defun cn7_txsimb (cn7_txsmb_sty cn7_txsmb_ali cn7_txsmb_value
		   cn7_txsmb_col cn7_txsmb_lay cn7_txsmb_ang)
  (guarda '("blipmode" "cecolor" "celtype" "clayer" "cmdecho" "orthomode"
          "textstyle" "luprec" "osmode" "dimzin"))
  (setq cn7_txtsty cn7_txsmb_sty)
  (cn7_text_hfinal)
  (cn7_text_height)
  (cn7_txsmb_wrtext)
  (devolve)
)

;direciona para model ou paper
(defun cn7_txsmb_wrtext ()
  (if (not (tblsearch "style" cn7_txtsty))
    (progn
      (cn7_alert_ok
	"O estilo solicitado não existe!"
	"Digite <CFG> para configurar o desenho!"
	"")
      (exit)
    )
    (progn
      (cn7_verylayer (strcat cn7_prefixlay cn7_txsmb_lay) cn7_txsmb_col)
      (ps_txtsmb);cond
    )
  )
)


;escreve num PSLD
(defun ps_txtsmb ()
  (if (/= "" cn7_txsmb_ali)
    (command "._text" "_s" cn7_txtsty cn7_txsmb_ali "_non" psimb_txt cn7_txth cn7_txsmb_ang cn7_txsmb_value)
    (command "._text" "_s" cn7_txtsty "_non" psimb_txt cn7_txth cn7_txsmb_ang cn7_txsmb_value)
  )
)


;******************************************************************************
;Função que verifica o status do layer requisitado: se não existir, será criado!!!
;******************************************************************************
(defun cn7_verylayer (cn7_very_layname cn7_laycol)
  (setq cn7_currlayer nil)
  ;se existe o layer solicitado
  (if (/= nil (setq cn7_currlayer (tblsearch "layer" cn7_very_layname)))
    (progn
      (setq cn7_layname (cdr (assoc 2 cn7_currlayer)))
      ;verifica se está desligado
      (if (= -30 (cdr (assoc 62 cn7_currlayer)))
	(progn
	  (cn7_alert_yes_no
	    "O layer solicitado está desligado!"
	    (strcat "layer = " cn7_layname)
	    "Deseja ligá-lo e Prosseguir?"
	  )
	  (if (= alert_resp "yes")
	    (command "._layer" "_on" cn7_layname "")
	    (exit)
	  )
	)
      );if
      (cond
	;se (assoc 70) é 1, está só freeze
	((= 1 (cdr (assoc 70 cn7_currlayer)))
	 (cn7_alert_yes_no
	   "O layer solicitado está congelado"
	   (strcat "layer = " cn7_layname)
	   "Deseja descongelá-lo e Prosseguir?"
	 )
	 (if (= alert_resp "yes")
	   (command "._layer" "_thaw" cn7_layname "")
	   (exit)
	 )
        )
	;se (assoc 70) é 4, é só lock
	((= 4 (cdr (assoc 70 cn7_currlayer)))
	 (cn7_alert_yes_no
	   "O layer solicitado está trancado"
	   (strcat "layer = " cn7_layname)
	   "Deseja destrancá-lo e Prosseguir?"
	 )
	 (if (= alert_resp "yes")
	   (command "._layer" "_unlock" cn7_layname "")
	   (exit)
	 )
        )
	;se (assoc 70) é 5, está freeze e lock
	((= 5 (cdr (assoc 70 cn7_currlayer)))
	 (cn7_alert_yes_no
	   "O layer solicitado está trancado e congelado!"
	   (strcat "layer = " cn7_layname)
	   "Deseja desfazer e Prosseguir?"
	 )
	 (if (= alert_resp "yes")
	   (progn
	     (command "._layer" "_unlock" cn7_layname "")
	     (command "._layer" "_thaw" cn7_layname "")
	   )
	   (exit)
	 )
        )
      );cond
      (command "._layer" "_m" cn7_very_layname "_c" cn7_laycol "" "");(setvar "clayer" cn7_very_layname)
    )
    (progn
      (command "._layer" "_m" cn7_very_layname "_c" cn7_laycol "" "")
      (prompt (strcat "...Criado layer <" (strcase cn7_very_layname) ">, com a cor <" (rtos cn7_laycol 2 0) ">."))
    )
  )
)

;******************************************************************************
;copia as shapes para o diretório de suporte
;******************************************************************************
; copy_shape definido no adaptador mac-port.lsp

;******************************************************************************
;função que identifica atualização
;******************************************************************************
(defun c:cn_about ()
  (setq open_file (open (strcat cnp_root "/config/about.txt") "r" "utf8"))
  (setq about_line1 (read-line open_file))
  (setq about_line2 (read-line open_file))
  (setq about_line3 (read-line open_file))
  (close open_file)
  (cn7_alert_ok about_line1 about_line2 about_line3)
  (princ)
)

;cnp_01

;******************************************************************************
;******************************************************************************
;FUNÇÕES DE MANIPULAÇÃO DE ESCALAS
;******************************************************************************
;******************************************************************************

;desliga escala selecionada
(defun c:ofe ()
  (if (and (= (getvar "tilemode") 0) (= (getvar "cvport") 1))
    (progn
      (alert "Operação só permitida\nno Model Space ou na Viewport!")
      (quit)
    )
  )
  (setq esc nil ent nil)
  (prompt "\nSelecione uma entidade base ou <ENTER> para digitar escala...")
  (setq ent (entsel))
  (if (= nil ent)
    ;se pressiona <ENTER>
    (progn
      (setq esc (getint "\nEntre com a escala a desligar..."))
      (if (/= nil esc)
	(progn
	  (fzv_blk_newlayer (getvar "clayer"))
	  (if (= (rtos esc 2 0) oldprefix)
	    ;se o layer atual pertence à escala a ser congelada
	    (progn
	      (alert "\nO layer atual pertence à escala a ser desligada!\nSelecione uma entidade para\ntornar seu layer atual e prosseguir...")
	      (setq ent (entsel))
	      (if (= nil ent)
		(exit)
		(progn
		  (setq ent_list (entget (car ent))
			ent_layer (cdr (assoc 8 ent_list))
		  )
		  (setvar "clayer" ent_layer)
		  (command "._layer" "_off" (strcat oldprefix "-*") "" "")
		  )
		);if
	      );progn T
	    ;se layer atual Não tem problema
	    (progn
	      (setvar "clayer" ent_layer)
	      (command "._layer" "_off" (strcat (rtos esc 2 0) "-*") "" "")
	    );progn F
	  )
	)
      );progn para o caso T, escala digitada
    )
    ;caso a escala a congelar seja definida por seleção de uma entidade
    (progn
      (setq ent_list (entget (car ent))
	    ent_layer (cdr (assoc 8 ent_list)))
      (fzv_verylayer)
      (if (member oldprefix reg_scale_list) (setq cve_xxxlist (append cve_xxxlist (list s1_ent))))
      (fzv_blk_newlayer ent_layer)
      (if (= oldprefix (substr (getvar "clayer") 1 (strlen oldprefix)))
	(progn
	  (alert "\nO layer atual pertence à escala a ser desligada!\nSelecione uma entidade para\ntornar seu layer atual e prosseguir...")
	  (setq ent (entsel))
	  (if (= nil ent)
	    (exit)
	    (progn
	      (setq ent_list (entget (car ent))
		    ent_layer (cdr (assoc 8 ent_list))
		    )
	      (setvar "clayer" ent_layer)
	      (command "._layer" "_off" (strcat oldprefix "-*") "" "")
	      )
	    );if
	 );progn
	(progn
	  (command "._layer" "_off" (strcat oldprefix "-*") "" "")
	)
      );if
    );progn
  )
  (princ)
)


;Congela escala selecionada
(defun c:fze ()
  (if (and (= (getvar "tilemode") 0) (= (getvar "cvport") 1))
    (progn
      (alert "Operação só permitida\nno Model Space ou na Viewport!")
      (quit)
      (princ)
    )
  )
  (setq esc nil ent nil)
  (prompt "\nSelecione uma entidade base ou <ENTER> para digitar escala...")
  (setq ent (entsel))
  (if (= nil ent)
    ;se pressiona <ENTER>
    (progn
      (setq esc (getint "\nEntre com a escala a congelar..."))
      (if (/= nil esc)
	(progn
	  (fzv_blk_newlayer (getvar "clayer"))
	  (if (= (rtos esc 2 0) oldprefix)
	    ;se o layer atual pertence à escala a ser congelada
	    (progn
	      (cn7_alert_ok
		"O layer atual pertence à escala a ser congelada!"
		"Selecione uma entidade para tornar seu layer atual"
		"e congelar a escala desejada..."
	      )
	      (setq ent (entsel))
	      (if (= nil ent)
		(exit)
		(progn
		  (setq ent_list (entget (car ent))
			ent_layer (cdr (assoc 8 ent_list))
		  )
		  (setvar "clayer" ent_layer)
		  (command "._layer" "_f" (strcat oldprefix "-*") "" "")
		  )
		);if
	      );progn T
	    ;se layer atual Não tem problema
	    (progn
	      (setvar "clayer" ent_layer)
	      (command "._layer" "_f" (strcat (rtos esc 2 0) "-*") "" "")
	    );progn F
	  )
	)
      );progn para o caso T, escala digitada
    )
    ;caso a escala a congelar seja definida por seleção de uma entidade
    (progn
      (setq ent_list (entget (car ent))
	    ent_layer (cdr (assoc 8 ent_list)))
      (fzv_verylayer)
      (if (member oldprefix reg_scale_list) (setq cve_xxxlist (append cve_xxxlist (list s1_ent))))
      (fzv_blk_newlayer ent_layer)
      (if (= oldprefix (substr (getvar "clayer") 1 (strlen oldprefix)))
	(progn
	  (cn7_alert_ok
		"O layer atual pertence à escala a ser congelada!"
		"Selecione uma entidade para tornar seu layer atual"
		"e congelar a escala desejada..."
	  )
	  (setq ent (entsel))
	  (if (= nil ent)
	    (exit)
	    (progn
	      (setq ent_list (entget (car ent))
		    ent_layer (cdr (assoc 8 ent_list))
		    )
	      (setvar "clayer" ent_layer)
	      (command "._layer" "_f" (strcat oldprefix "-*") "" "")
	      )
	    );if
	 );progn
	(progn
	  (command "._layer" "_f" (strcat oldprefix "-*") "" "")
	)
      );if
    );progn
  )
  (princ)
)

;Congela escala selecionada na Viewport
(defun c:fzv ()
  ;veryfica se está na Viewport
  (if (or
	(= (getvar "tilemode") 1)
	(and (= (getvar "tilemode") 0) (= (getvar "cvport") 1))
      )
    (progn
      (alert "Operação só permitida\nna Viewport!")
      (quit)
    )
  )
  (setq esc nil ent nil)
  (prompt "\nSelecione uma entidade base ou <ENTER> para digitar escala...")
  (setq ent (entsel))
  (if (= nil ent)
    ;se pressiona <ENTER>
    (progn
      (setq esc (getint "\nEntre com a escala a congelar..."))
      (if (/= nil esc)
	(progn
	  (fzv_blk_newlayer (getvar "clayer"))
	  (if (= (rtos esc 2 0) oldprefix)
	    ;se o layer atual pertence à escala a ser congelada
	    (progn
	      (cn7_alert_ok
		"O layer atual pertence à escala a ser congelada!"
		"Selecione uma entidade para tornar seu layer atual"
		"e congelar a escala desejada..."
	      )
	      (setq ent (entsel))
	      (if (= nil ent)
		(exit)
		(progn
		  (setq ent_list (entget (car ent))
			ent_layer (cdr (assoc 8 ent_list))
		  )
		  (setvar "clayer" ent_layer)
		  (command "._vplayer" "_f" (strcat oldprefix "-*") "" "")
		  )
		);if
	      );progn T
	    ;se layer atual Não tem problema
	    (progn
	      (setvar "clayer" ent_layer)
	      (command "._vplayer" "_f" (strcat (rtos esc 2 0) "-*") "" "")
	    );progn F
	  )
	)
      );progn para o caso T, escala digitada
    )
    ;caso a escala a congelar seja definida por seleção de uma entidade
    (progn
      (setq ent_list (entget (car ent))
	    ent_layer (cdr (assoc 8 ent_list)))
      (fzv_verylayer)
      (if (member oldprefix reg_scale_list) (setq cve_xxxlist (append cve_xxxlist (list s1_ent))))
      (fzv_blk_newlayer ent_layer)
      (if (= oldprefix (substr (getvar "clayer") 1 (strlen oldprefix)))
	(progn
	  (cn7_alert_ok
		"O layer atual pertence à escala a ser congelada!"
		"Selecione uma entidade para tornar seu layer atual"
		"e congelar a escala desejada..."
	  )
	  (setq ent (entsel))
	  (if (= nil ent)
	    (exit)
	    (progn
	      (setq ent_list (entget (car ent))
		    ent_layer (cdr (assoc 8 ent_list))
		    )
	      (setvar "clayer" ent_layer)
	      (command "._vplayer" "_f" (strcat oldprefix "-*") "" "")
	      )
	    );if
	 );progn
	(progn
	  (command "._vplayer" "_f" (strcat oldprefix "-*") "" "")
	)
      );if
    );progn
  );if
  (princ)
);defun

;verifica se o layer desejado como current é válido.
(defun fzv_verylayer ()
  (setq counter2 1 oldprefix "")
  (while (and
	   (/= "-" (substr ent_layer counter2 1))
	   (/= ""  (substr ent_layer counter2 1))
	 );and
    (setq oldprefix (strcat oldprefix (substr ent_layer counter2 1))
	  counter2 (1+ counter2)
    )
  )
  (if (member oldprefix reg_scale_list)
    (progn
      (setq counter2 (1+ counter2)
	    layer_sufix (substr ent_layer counter2))
    )
    (progn
      (alert "\nEntidade não gráfica\nou layer inválido!")
      (quit)
    )
  )
  (princ)
)

;auxiliar para encontrar o prefixo do layer
(defun fzv_blk_newlayer (layer_name)
  (setq n_oldlayer (strlen layer_name) counter2 1 oldprefix "" layer_sufix "")
  (while (/= "-" (substr layer_name counter2 1))
    (setq oldprefix (strcat oldprefix (substr layer_name counter2 1))
	  counter2 (1+ counter2)
    )
  )
  (if (member oldprefix reg_scale_list)
    (progn
      (setq counter2 (1+ counter2)
	    layer_sufix (substr layer_name counter2))
    )
    (progn
      (alert "Escala não regular!")
      (quit)
    )
  )
  (princ)
)
  
;liga escala
(defun c:one ()
  (setq esc (getint "\nEntre com a escala a ligar..."))
  (if (/= nil esc)
    (command "._layer" "_on" (strcat (rtos esc 2 0) "-*") "")
  )
  (princ)
)
	  

;descongela escala
(defun c:twe ()
  (setq esc (getint "\nEntre com a escala a descongelar..."))
  (if (/= nil esc)
    (command "._layer" "_thaw" (strcat (rtos esc 2 0) "-*") "")
  )
  (princ)
)

;descongela escala na Viewport
(defun c:twv ()
  (if (or
	(= (getvar "tilemode") 1)
	(and (= (getvar "tilemode") 0) (= (getvar "cvport") 1))
      )
    (progn
      (alert "Operação só permitida\nna Viewport!")
      (quit)
    )
  )
  (setq esc (getint "\nEntre com a escala a descongelar..."))
  (if (/= nil esc)
    (command "._vplayer" "_thaw" (strcat (rtos esc 2 0) "-*") "" "")
  )
  (princ)
)

;cnp_02


;************************************************************************
;CONVERSÃO DE ESCALAS
;************************************************************************

;converter escala
(defun c:cve ()
  (command "._undo" "_m")
  (setq key "convert")
  (cve_init)
  (prompt "\nDigite <UB> para voltar...")
  (princ)
)

;copiar para escala
(defun c:cpe ()
  (command "._undo" "_m")
  (setq cts_newscale nil)
  (if (= (getvar "tilemode") 0)
    (progn
      (alert "Operação só permitida\nno Model Space!")
      (quit)
    )
  )
  (setq cts_newscale (getint "\nEscala para cópia = 1: "))
  (if (= nil cts_newscale) (quit))
  (setq key "copy")
  (cve_init)
  (prompt "\nDigite <UB> para voltar...")
  (princ)
)

  

;conversão de escalas
;só permitida na viewport e no Model Pleno, não no Paper
(defun cve_init ()
  (if (and (= (getvar "tilemode") 0) (= (getvar "cvport") 1))
    (progn
      (alert "Operação só permitida\nno Model Space ou na Viewport!")
      (quit)
    )
  )
  (setq cn7_upscale_id nil)
  (cn7_init)
  ;define a escala final de conversão
  (if (= (getvar "tilemode") 1);se está no Model
    (progn
      (setq grp_type "2")
      (cn7_find_blkscl)
      (if (= nil cn7_msscl) (cn7_esc))
    )
    (progn			;se está na Viewport
      (cn7_vport_scl)
      (setq cn7_msscl cn7_vp_scale)
    )
  )
  (setq cve_newscl cn7_msscl)


  ;abre a caixa de diálogo
  (setq dcl_id (load_dialog (strcat cnp_root "/lisp/cadnorma.dcl")))
  (if (not (new_dialog "cn7_upscale" dcl_id)) (exit))

  ;define Model ou Viewport. Edit_box em grayout
  (if (= key "convert")
    (set_tile "cn7_cve_newscl" (strcat "Convertendo para Escala 1: "  (rtos cve_newscl 2 0)))
    (set_tile "cn7_cve_newscl" (strcat "Copiando para Escala 1: "  (rtos cts_newscale 2 0)))
  )
  (setq upscale_txt "1")
  (set_tile "cn7_upscale_txt" "1")
  (action_tile "cn7_upscale_txt" "(setq upscale_txt $value)")
  (setq upscale_dim "1")
  (set_tile "cn7_upscale_dim" "1")
  (action_tile "cn7_upscale_dim" "(setq upscale_dim $value)")
  (setq upscale_blk "1")
  (set_tile "cn7_upscale_blk" "1")
  (action_tile "cn7_upscale_blk" "(setq upscale_blk $value)")
  (action_tile "accept" "(done_dialog 1)")
  (action_tile "cancel" "(done_dialog 0)")
  (setq cn7_upscale_id (start_dialog))
  (unload_dialog dcl_id)
  (if (= cn7_upscale_id 1)
    (progn
      (cn7_cve_seleciona)
      (if (/= nil cve_sel)
	(if (= key "convert")
	  (progn
	    (cn7_cve_separa)
	    (cn7_cve_heart)
	  )
	  (progn
	    (setq old_msscl cn7_msscl)
	    (setq cn7_msscl cts_newscale)
	    (cn7_cve_separa)
	    (cts_select)
	    (command "._copy" cts_selection "" "_non" "0,0,0" "")
	    (cn7_cve_heart)
	    (setq cn7_msscl old_msscl)
	  )
	)
      )
    )
  )
  (princ)
)


;seleciona as entidades a serem copiadas para outra escala
(defun cts_select ()
  (setq counter 0 cts_selection (ssadd))
  (if (/= nil cve_txtlist)
    (progn
      (setq n_list (length cve_txtlist))
      (repeat n_list
	(ssadd (nth counter cve_txtlist) cts_selection)
	(setq counter (1+ counter))
      )
    )
  )
  (setq counter 0)
  (if (/= nil cve_dimlist)
    (progn
      (setq n_list (length cve_dimlist))
      (repeat n_list
	(ssadd (nth counter cve_dimlist) cts_selection)
	(setq counter (1+ counter))
      )
    )
  )
  (setq counter 0)
  (if (/= nil cve_blklist)
    (progn
      (setq n_list (length cve_blklist))
      (repeat n_list
	(ssadd (nth counter cve_blklist) cts_selection)
	(setq counter (1+ counter))
      )
    )
  )
  (setq counter 0)
  (if (/= nil cve_xxxlist)
    (progn
      (setq n_list (length cve_xxxlist))
      (repeat n_list
	(ssadd (nth counter cve_xxxlist) cts_selection)
	(setq counter (1+ counter))
      )
    )
  )
)

;seleção de entidades
(defun cn7_cve_seleciona ()
  (prompt "\nSelecione o trecho do desenho a ser convertido...")
  (setq cve_sel (ssget))
)

;cria 03 listas, com textos, cotas e blocos separados
(defun cn7_cve_separa ()
  (setq cve_txtlist (list " ")
	cve_dimlist (list " ")
	cve_blklist (list " ")
	cve_xxxlist (list " ")
	n_element (sslength cve_sel)
	counter 0)
  (repeat n_element
    (setq s1_ent (ssname cve_sel counter))
    (setq ent_list (entget s1_ent))
    (if	(= (strcase (cdr (assoc 0 ent_list))) "TEXT")
      (setq cve_txtlist (append cve_txtlist (list s1_ent)))
      (if (= (strcase (cdr (assoc 0 ent_list))) "DIMENSION")
	(setq cve_dimlist (append cve_dimlist (list s1_ent)))
	(if (= (strcase (cdr (assoc 0 ent_list))) "INSERT")
	  (setq cve_blklist (append cve_blklist (list s1_ent)))
	  (cve_ent_verylayer)
        )
      )
    )
    (setq counter (1+ counter))
  )
  (setq cve_txtlist (cdr cve_txtlist)
	cve_dimlist (cdr cve_dimlist)
	cve_blklist (cdr cve_blklist)
	cve_xxxlist (cdr cve_xxxlist)
  )
)


;verifica e altera o layer de entidades gráficas
(defun cve_ent_verylayer ()
  (setq ent_layer (cdr (assoc 8 ent_list)))
  (setq n_oldlayer (strlen ent_layer) counter2 1 oldprefix "")
  (while
    (and
      (/= "" (substr ent_layer counter2 1))
      (/= "-" (substr ent_layer counter2 1))
    )
    (setq oldprefix (strcat oldprefix (substr ent_layer counter2 1))
	  counter2 (1+ counter2)
    )
  )
  (if (member oldprefix reg_scale_list) (setq cve_xxxlist (append cve_xxxlist (list s1_ent))))
)

;verifica a cor correspondente ao layer selecionado
(defun cve_ent_verycolor (lay_name)
  (cond
    ((= (strcase lay_name) "A-ALVA-F") (setq lay_color 4))
    ((= (strcase lay_name) "P-ESQD-F") (setq lay_color 122))
    ((= (strcase lay_name) "A-ALVA-M") (setq lay_color 161))
    ((= (strcase lay_name) "A-ALVA-G") (setq lay_color 5))
    ((= (strcase lay_name) "A-CONST-F") (setq lay_color 246))
    ((= (strcase lay_name) "A-CONST-G") (setq lay_color 242))
    ((= (strcase lay_name) "A-CONST-M") (setq lay_color 244))
    ((= (strcase lay_name) "A-CVER-F") (setq lay_color 121))
    ((= (strcase lay_name) "A-DEMO-F") (setq lay_color 40))
    ((= (strcase lay_name) "A-DEMO-G") (setq lay_color 38))
    ((= (strcase lay_name) "A-DIMS-F") (setq lay_color 152))
    ((= (strcase lay_name) "A-DIVI-F") (setq lay_color 12))
    ((= (strcase lay_name) "A-DIVI-M") (setq lay_color 47))
    ((= (strcase lay_name) "A-DIVI-G") (setq lay_color 18))
    ((= (strcase lay_name) "A-ESQD-F") (setq lay_color 132))
    ((= (strcase lay_name) "A-ESQD-M") (setq lay_color 124))
    ((= (strcase lay_name) "A-NIVEL-F") (setq lay_color 212))
    ((= (strcase lay_name) "A-PAG-F") (setq lay_color 53))
    ((= (strcase lay_name) "A-PISO-F") (setq lay_color 81))
    ((= (strcase lay_name) "A-PISO-G") (setq lay_color 94))
    ((= (strcase lay_name) "A-PRTA-F") (setq lay_color 8))
    ((= (strcase lay_name) "A-PRTA-M") (setq lay_color 26))
    ((= (strcase lay_name) "A-RBXO-F") (setq lay_color 225))
    ((= (strcase lay_name) "A-RBXO-G") (setq lay_color 230))
    ((= (strcase lay_name) "A-TELH-F") (setq lay_color 57))
    ((= (strcase lay_name) "U-LMTS-F") (setq lay_color 2))
    ((= (strcase lay_name) "A-TELH-G") (setq lay_color 39))
    ((= (strcase lay_name) "ABL") (setq lay_color 61))
    ((= (strcase lay_name) "ATC") (setq lay_color 3))
    ((= (strcase lay_name) "ATP") (setq lay_color 241))
    ((= (strcase lay_name) "ATP-VAR") (setq lay_color 242))
    ((= (strcase lay_name) "ATE") (setq lay_color 181))
    ((= (strcase lay_name) "AREA") (setq lay_color 30))
    ((= (strcase lay_name) "E-COZI-F") (setq lay_color 55))
    ((= (strcase lay_name) "E-GRAD-F") (setq lay_color 36))
    ((= (strcase lay_name) "E-GRAD-M") (setq lay_color 158))
    ((= (strcase lay_name) "E-MOBI-F") (setq lay_color 100))
    ((= (strcase lay_name) "E-SANI-F") (setq lay_color 42))
    ((= (strcase lay_name) "G-EIXO-F") (setq lay_color 60))
    ((= (strcase lay_name) "G-FHCT-F") (setq lay_color 201))
    ((= (strcase lay_name) "G-FIG-F") (setq lay_color 18))
    ((= (strcase lay_name) "G-RGRAF-F") (setq lay_color 134))
    ((= (strcase lay_name) "G-HCHR-F") (setq lay_color 41))
    ((= (strcase lay_name) "G-HCHR-G") (setq lay_color 193))
    ((= (strcase lay_name) "G-IDEN-F") (setq lay_color 243))
    ((= (strcase lay_name) "G-MASC-F") (setq lay_color 110))
    ((= (strcase lay_name) "G-SOL1-F") (setq lay_color 254))
    ((= (strcase lay_name) "G-SOL2-F") (setq lay_color 253))
    ((= (strcase lay_name) "G-SOL3-F") (setq lay_color 252))
    ((= (strcase lay_name) "G-SOL4-F") (setq lay_color 251))
    ((= (strcase lay_name) "G-VAZIO-F") (setq lay_color 131))
    ((= (strcase lay_name) "I-ACND-F") (setq lay_color 32))
    ((= (strcase lay_name) "I-ELTR-F") (setq lay_color 21))
    ((= (strcase lay_name) "I-ESG-F") (setq lay_color 165))
    ((= (strcase lay_name) "I-ESP-F") (setq lay_color 44))
    ((= (strcase lay_name) "I-GAS-F") (setq lay_color 210))
    ((= (strcase lay_name) "I-HDRO-F") (setq lay_color 62))
    ((= (strcase lay_name) "I-INC-F") (setq lay_color 175))
    ((= (strcase lay_name) "I-LUMI-F") (setq lay_color 190))
    ((= (strcase lay_name) "I-TELE-F") (setq lay_color 91))
    ((= (strcase lay_name) "M-MARG-F") (setq lay_color 51))
    ((= (strcase lay_name) "M-TABS-F") (setq lay_color 9))
    ((= (strcase lay_name) "P-ACND-F") (setq lay_color 31))
    ((= (strcase lay_name) "P-ESTR-F") (setq lay_color 50))
    ((= (strcase lay_name) "P-INF-F") (setq lay_color 240))
    ((= (strcase lay_name) "P-SUP-F") (setq lay_color 200))
    ((= (strcase lay_name) "S-ESTR-F") (setq lay_color 202))
    ((= (strcase lay_name) "S-ESTR-G") (setq lay_color 1))
    ((= (strcase lay_name) "T-AREA-F") (setq lay_color 20))
    ((= (strcase lay_name) "T-COMP-G") (setq lay_color 255))
    ((= (strcase lay_name) "T-ESTR-F") (setq lay_color 250))
    ((= (strcase lay_name) "T-TEXT-F") (setq lay_color 214))
    ((= (strcase lay_name) "U-AGUA-F") (setq lay_color 141))
    ((= (strcase lay_name) "U-AFST-F") (setq lay_color 35))
    ((= (strcase lay_name) "U-CURV-F") (setq lay_color 48))
    ((= (strcase lay_name) "U-ESTC-F") (setq lay_color 237))
    ((= (strcase lay_name) "U-VSIM-F") (setq lay_color 237))
    ((= (strcase lay_name) "U-VDUP-F") (setq lay_color 237))
    ((= (strcase lay_name) "U-MFIO-F") (setq lay_color 120))
    ((= (strcase lay_name) "U-URBA-F") (setq lay_color 154))
    ((= (strcase lay_name) "V-ARV-F") (setq lay_color 96))
    ((= (strcase lay_name) "V-VGTO-F") (setq lay_color 98))
    ((= (strcase lay_name) "G-FURO-F") (setq lay_color 7))
  )
)

  
;função carburador
(defun cn7_cve_heart ()
  (setq grp_type "2")
  (cn7_find_blkscl)
  (princ)
  (if (and (/= nil cve_txtlist) (= upscale_txt "1")) (cve_uptxt))
  (if (and (/= nil cve_dimlist) (= upscale_dim "1")) (cve_updim))
  (if (and (/= nil cve_blklist) (= upscale_blk "1")) (cve_upblk))
  ;(if (/= nil cve_xxxlist) (cve_upxxx))
)


;altera o layer de entidades gráficas
(defun cve_upxxx ()
  (setq counter 0
	n_xxxlist (length cve_xxxlist))
  
  (repeat n_xxxlist
    (setq ent_name (nth counter cve_xxxlist)
	  ent_list (entget ent_name)
	  ent_layer (cdr (assoc 8 ent_list))
	  n_oldlayer (strlen ent_layer)
	  counter2 1
	  oldprefix "")
    (while (/= "-" (substr ent_layer counter2 1))
      (setq oldprefix (strcat oldprefix (substr ent_layer counter2 1))
	    counter2 (1+ counter2)
      )
    )
    (setq counter2 (1+ counter2)
	  layer_sufix (substr ent_layer counter2))
;;;    (cve_ent_verycolor layer_sufix)
    (cn7_verylayer (strcat cn7_blk_prefixlay layer_sufix) lay_color)
    (setq ent_list (entmod (subst (cons 8 (strcat cn7_blk_prefixlay layer_sufix)) (assoc 8 ent_list) ent_list)))
    (setq cve_xxxlist (append cve_xxxlist (list s1_ent)))
    (setq counter (1+ counter))
  )
)


;conversão de textos
(defun cve_uptxt ()
  (setq n_element (length cve_txtlist) counter 0)
  (repeat n_element
    (setq s1_ent (nth counter cve_txtlist))
    ;determina o layer do texto
    (setq ent_list (entget s1_ent))
    ;determina o estilo do texto
    (setq curr_txtstyle (strcase (cdr (assoc 7 ent_list))))
    (cond
      ;estilo romans
      ((= curr_txtstyle "R50")
       (setq new_txtheight 1.25)
       (cve_txt_chgsty)
       (cve_uptxt_checklay)
       (setq counter (1+ counter))
       )
      ((= curr_txtstyle "R60")
       (setq new_txtheight 1.5)
       (cve_txt_chgsty)
       (cve_uptxt_checklay)
       (setq counter (1+ counter))
       )
      ((= curr_txtstyle "R70")
       (setq new_txtheight 1.75)
       (cve_txt_chgsty)
       (cve_uptxt_checklay)
       (setq counter (1+ counter))
       )
      ((= curr_txtstyle "R80")
       (setq new_txtheight 2.0)
       (cve_txt_chgsty)
       (cve_uptxt_checklay)
       (setq counter (1+ counter))
       )
      ((= curr_txtstyle "R90")
       (setq new_txtheight 2.25)
       (cve_txt_chgsty)
       (cve_uptxt_checklay)
       (setq counter (1+ counter))
       )
      ((= curr_txtstyle "R100")
       (setq new_txtheight 2.5)
       (cve_txt_chgsty)
       (cve_uptxt_checklay)
       (setq counter (1+ counter))
       )
      ((= curr_txtstyle "R120")
       (setq new_txtheight 3.0)
       (cve_txt_chgsty)
       (cve_uptxt_checklay)
       (setq counter (1+ counter))
       )
      ((= curr_txtstyle "R140")
       (setq new_txtheight 3.5)
       (cve_txt_chgsty)
       (cve_uptxt_checklay)
       (setq counter (1+ counter))
       )
      ((= curr_txtstyle "R175")
       (setq new_txtheight 4.375)
       (cve_txt_chgsty)
       (cve_uptxt_checklay)
       (setq counter (1+ counter))
       )
      ((= curr_txtstyle "R200")
       (setq new_txtheight 5.0)
       (cve_txt_chgsty)
       (cve_uptxt_checklay)
       (setq counter (1+ counter))
      )
      ;custom_text_styles
      ((= curr_txtstyle "T1")
       (cn7_cfg_altext_file)
       (setq new_txtheight (distof t1_alt))
       (cve_txt_chgsty)
       (cve_uptxt_checklay)
       (setq counter (1+ counter))
      )
      ((= curr_txtstyle "T2")
       (cn7_cfg_altext_file)
       (setq new_txtheight (distof t2_alt))
       (cve_txt_chgsty)
       (cve_uptxt_checklay)
       (setq counter (1+ counter))
      )
      ((= curr_txtstyle "T3")
       (cn7_cfg_altext_file)
       (setq new_txtheight (distof t3_alt))
       (cve_txt_chgsty)
       (cve_uptxt_checklay)
       (setq counter (1+ counter))
      )
      ((= curr_txtstyle "T4")
       (cn7_cfg_altext_file)
       (setq new_txtheight (distof t4_alt))
       (cve_txt_chgsty)
       (cve_uptxt_checklay)
       (setq counter (1+ counter))
      )
      ((= curr_txtstyle "T5")
       (cn7_cfg_altext_file)
       (setq new_txtheight (distof t5_alt))
       (cve_txt_chgsty)
       (cve_uptxt_checklay)
       (setq counter (1+ counter))
      )
      ((= curr_txtstyle "T6")
       (cn7_cfg_altext_file)
       (setq new_txtheight (distof t6_alt))
       (cve_txt_chgsty)
       (cve_uptxt_checklay)
       (setq counter (1+ counter))
      )
      ((= curr_txtstyle "T7")
       (cn7_cfg_altext_file)
       (setq new_txtheight (distof t7_alt))
       (cve_txt_chgsty)
       (cve_uptxt_checklay)
       (setq counter (1+ counter))
      )
      (t 
       (setq counter (1+ counter))
      )
  );cond
 );repeat
)
;verifica se o texto está em um layer gráfico e muda para
(defun cve_uptxt_checklay ()
  (setq ent_layer (cdr (assoc 8 ent_list))
        n_oldlayer (strlen ent_layer) counter2 1 oldprefix "")
  (setq cve_uptxt_newlaycolor (cdr (assoc 62 (tblsearch "layer" ent_layer))))
  ;verifica se o texto contém um prefixo de escala (oldprefix)
  (while
    (and
      (/= "" (substr ent_layer counter2 1))
      (/= "-" (substr ent_layer counter2 1))
    )
    (setq oldprefix (strcat oldprefix (substr ent_layer counter2 1))
	  counter2 (1+ counter2)
    )
  )
  ;verifica se o prefixo pertence a uma escala regular
  (if (member oldprefix reg_scale_list)
    (progn
      (setq ent_laysufix (substr ent_layer (+ 2 (strlen oldprefix)))
	    cve_uptxt_newlayer (strcat cn7_blk_prefixlay ent_laysufix))
      (cn7_verylayer cve_uptxt_newlayer cve_uptxt_newlaycolor)
      (setq ent_list (entmod (subst (cons 8 cve_uptxt_newlayer) (assoc 8 ent_list) ent_list)))
    )
  )
)


;altera a altura e o layer do texto
(defun cve_txt_chgsty ()
  (setq ent_list
	 (entmod (subst
		   (cons 40
			 (cond
			   ((= cn7_dwgunit 1.0) (/ (* cn7_msscl new_txtheight) 1000.000))
			   ((= cn7_dwgunit 100.0) (/ (* cn7_msscl new_txtheight) 10.000))
			   ((= cn7_dwgunit 1000.0) (/ (* cn7_msscl new_txtheight) 1.000))
			  )
		   )
		   (assoc 40 ent_list)
		   ent_list))
  )
)


;conversão de cotas
(defun cve_updim ()
  (setq n_element (length cve_dimlist) counter 0 dimmo (getvar "dimstyle") dimscl (getvar "dimscale"))
  (setq s1_dim (ssadd)) 
  (repeat n_element
    (ssadd (nth counter cve_dimlist) s1_dim )
    (setq counter (1+ counter))
  )
  ;separa as cotas em 5 listas
  (setq counter 0 cve_dim1 (ssadd) cve_dim2 (ssadd) cve_dim3 (ssadd) cve_dim4 (ssadd) cve_dim5 (ssadd))
  (repeat n_element
    (setq s1_ent (nth counter cve_dimlist))
    ;determina o estilo da cota
    (setq ent_list (entget s1_ent)
	  ent_dimsty (strcase (cdr (assoc 3 ent_list)))
    )
    (cond
      ((= ent_dimsty "CADNORMA_DIM1") (ssadd (nth counter cve_dimlist) cve_dim1))
      ((= ent_dimsty "CADNORMA_DIM2") (ssadd (nth counter cve_dimlist) cve_dim2))
      ((= ent_dimsty "CADNORMA_DIM3") (ssadd (nth counter cve_dimlist) cve_dim3))
      ((= ent_dimsty "CADNORMA_DIM4") (ssadd (nth counter cve_dimlist) cve_dim4))
      ((= ent_dimsty "CADNORMA_DIM5") (ssadd (nth counter cve_dimlist) cve_dim5))
    )
    ;transforma o layer das cota
    (cve_uptxt_checklay)
    (setq counter (1+ counter))
  )
  ;agora vai atuar diferente no paper ou no model
  (if (/= 0 (sslength cve_dim1))
    (progn
      (command "._dimstyle" "_r" "CADNORMA_DIM1")
      (cve_updim_checkscale)
      (command "._dim1" "_update" cve_dim1 "")
    )
  )
  (if (/= 0 (sslength cve_dim2))
    (progn
      (command "._dimstyle" "_r" "CADNORMA_DIM2")
      (cve_updim_checkscale)
      (command "._dim1" "_update" cve_dim2 "")
    )
  )
  (if (/= 0 (sslength cve_dim3))
    (progn
      (command "._dimstyle" "_r" "CADNORMA_DIM3")
      (cve_updim_checkscale)
      (command "._dim1" "_update" cve_dim3 "")
    )
  )
  (if (/= 0 (sslength cve_dim4))
    (progn
      (command "._dimstyle" "_r" "CADNORMA_DIM4")
      (cve_updim_checkscale)
      (command "._dim1" "_update" cve_dim4 "")
    )
  )
  (if (/= 0 (sslength cve_dim5))
    (progn
      (command "._dimstyle" "_r" "CADNORMA_DIM5")
      (cve_updim_checkscale)
      (command "._dim1" "_update" cve_dim5 "")
    )
  )
  (command "._dimstyle" "_r" dimmo)
  (setvar "dimscale" dimscl)
  (princ)
)

;avalia o dimscale
(defun cve_updim_checkscale ()
  (if (= 1 (getvar "tilemode"));Model Space
    (cond
      ((= cn7_dwgunit 1.0) (setvar "dimscale" (/ cn7_msscl 1000.00)))
      ((= cn7_dwgunit 100.0) (setvar "dimscale" (/ cn7_msscl 10.00)))
      ((= cn7_dwgunit 1000.0) (setvar "dimscale" cn7_msscl))
     )
    (setvar "dimscale" 0.00)
  )
)

;função que corrige a escala dos blocos......
(defun cve_upblk ()
  (setq n_element (length cve_blklist) counter 0)
  (setq s1_blk (ssadd)
	cve_private_blk ; blocos privados
	 (list "cvg_ex1" "cvg_ex2" "cvg_ex3" "crt1_b1" "crt1_b2" "crt2_2"
	       "cvg_id1" "cvg_id2" "cvg_id3" "cvg_id4" "cvg_id5" "cvg_id6" "cvg_id7"
	       "cvg_id8" "cvg_id9" "cvg_id10" "cvg_id11" "cvg_id12" "cvg_id13" "cvg_id14"
	       "cvg_id15" "cvg_id16" "cvg_id17" "cvg_id18" "cvg_id19" "cvg_id20"
	       "tub_tcol1" "tub_tcol2" "idcol" "tp_loc_topog" "dsnv1"
	       "ele_circ_n" "ele_circ_f" "ele_circ_r" "ele_circ_t" "ele_circ_c" "cvg_incl"
	       "cvg_nvc2" "cvg_nvc2a" "cvg_nvp1" "cvg_nvp2" "cvg_tt1" "cvg_tt2" "cvg_tt3"
	       "cvg_tt4" "cvg_tt5" "cvg_tt6" "cvg_tt7" "cvg_tt8" "crt1_b1" "crt1_b2" "crt2_b2"
	       "cvg_ex1" "cvg_ex2" "cvg_ex3" "cvg_id1" "cvg_id2" "cvg_id3" "cvg_id4" "cvg_id5" "cvg_id6"
	       "cvg_id7" "cvg_id8" "cvg_id9" "cvg_id10" "cvg_id11" "cvg_id12" "cvg_id13" "cvg_id14" "cvg_id15" "cvg_id16")
  )
  ;o repeat abaixo separa os blocos gráficos
  (repeat n_element
    (setq s1_ent (nth counter cve_blklist))
    (setq ent_list (entget s1_ent)
	  ent_blkname (cdr (assoc 2 ent_list)))
    (if (member ent_blkname cve_private_blk);blocos privados
      (ssadd (nth counter cve_blklist) s1_blk)
      (progn
	(if (findfile (strcat cnp_root "/blocos/" ent_blkname ".dwg"))
	  (progn
	    (setq cve_blk_group_file (strcat cnp_root"/slides/" (substr ent_blkname 1 10) ".sgp"))
	    (if (findfile cve_blk_group_file)
	      (progn
		(setq cve_blk_group_open (open cve_blk_group_file "r" "utf8")
		      cve_blk_blktype (read-line cve_blk_group_open)
		      cve_blk_blkunit (read-line cve_blk_group_open)
		)
		(close cve_blk_group_open)
		(if (= "2" cve_blk_blktype);se o bloco for gráfico, vai para a lista
		  (ssadd (nth counter cve_blklist) s1_blk )
		)
	      )
	    )
	  );progn
	)
      )	  
    )
    (setq counter (1+ counter))
  );repeat
  ;altera a escala dos blocos
  (setq n_repeat (sslength s1_blk) counter 0)
  (repeat n_repeat
    (setq entname (ssname s1_blk counter)
	  ent_list (entget entname)
	  ent_scale (cdr (assoc 41 ent_list))
	  ent_layer (cdr (assoc 8 ent_list))
	  ent_layer_color (cdr (assoc 62 (tblsearch "layer" ent_layer))))
    (cve_blk_newlayer ent_layer)
    (setq new_layername (strcat cn7_blk_prefixlay layer_sufix))
    (cn7_verylayer new_layername ent_layer_color)
    (setq ent_list (entmod (subst (cons 8 new_layername) (assoc 8 ent_list) ent_list)))
    (command "._scale" entname "" "_non" (cdr (assoc 10 ent_list)) "_r" (abs ent_scale) cn7_blkscl)
    (setq counter (1+ counter))
  )
  ;altera o layer dos blocos
)

;acha o sufixo (layer_sufix) e o prefixo do layer (oldprefix)
(defun cve_blk_newlayer (layer_name)
  (setq n_oldlayer (strlen layer_name) counter2 1 oldprefix "" layer_sufix "")
  (while (/= "-" (substr layer_name counter2 1))
    (setq oldprefix (strcat oldprefix (substr layer_name counter2 1))
	  counter2 (1+ counter2)
    )
  )
  (if (member oldprefix reg_scale_list)
    (progn
      (setq counter2 (1+ counter2)
	    layer_sufix (substr layer_name counter2))
    )
    (progn
      (alert "\nEntidade não gráfica\nou layer inválido!")
      (quit)
    )
  )
)

;cnp_03
  

;******************************************************************************
;******************************************************************************
;Ferramentas do Paper Space
;******************************************************************************
;******************************************************************************
;tranca as janelas selecionadas
(defun c:vp_lock ()
  (guarda '("blipmode" "cecolor" "celtype" "clayer" "cmdecho" "orthomode"
          "textstyle" "luprec" "osmode" "dimzin"))
  (if (= 1 (getvar "tilemode"))
    (progn
      (cn7_alert_ok
	"Você está operando no Model Space."
	"Esta operação não é permitida aqui!"
	"Mude para o Paper Space...")
    (exit)
    )
  )
  (command "._pspace")
  (prompt "\nSelecione as Viewports que deseja trancar...")
  (setq cn7_vp_tolock (ssget '((0 . "VIEWPORT"))))
  (command "._mview" "_lock" "_on" cn7_vp_tolock "")
  (devolve)
  (princ)
)

;destranca as janelas selecionadas
(defun c:vp_unlock ()
  (if (= 1 (getvar "tilemode"))
    (progn
      (cn7_alert_ok
	"Você está operando no Model Space."
	"Esta operação não é permitida aqui!"
	"Mude para o Paper Space...")
    (exit)
    )
  )
  (command "._pspace")
  (prompt "\nSelecione as Viewports que deseja destrancar...")
  (setq cn7_vp_tolock (ssget '((0 . "VIEWPORT"))))
  (command "._mview" "_lock" "_off" cn7_vp_tolock "")
  (princ)
)

;************************************************************************
;DEFINE A ESCALA DE UMA JANELA
;************************************************************************

;atalho de teclado
(defun c:vp_xp ()
  (setq curr_scale nil cn7_vp_scale nil)
  (cn7_init)
  (cn7_very_ispaper)
  (cn7_vport_scl);retorna <cn7_vp_scale>
  (cn7_vp_zxp)
  (princ)
)


;abre a dcl e retorna a escala desejada
(defun cn7_vp_zxp ()
  (setq alert_resp nil v1 nil v2 nil)
  (cn7_verylocked)
  (setq dcl_id (load_dialog (strcat cnp_root "/lisp/cadnorma.dcl")))
  (if (not (new_dialog "cn7_vwpesc" dcl_id)) (exit))
  (if cn7_vp_scale
    (set_tile "cn7_vwpesc_esc_atual" (strcat "Escala Atual = 1: " (rtos cn7_vp_scale 2 0)))
  )
  (mode_tile "cn7_vwpesc_esc" 2)
  (action_tile "cn7_vwpesc_esc" "(cn7_vwpesc_veryget)")
  (action_tile "accept" "(done_dialog 1)")
  (action_tile "cancel" "(done_dialog 0)")
  (setq zxp_resp (start_dialog))
  (unload_dialog dcl_id)
  (if (= 1 zxp_resp)
    (progn
      (initget 1)
      (setq zxp_cenpt (getpoint "Clique no ponto de centralização da imagem..."))
      (if (and (/= curr_scale 1.25) (/= curr_scale 1.5) (/= curr_scale 12.5) (/= curr_scale 2.5) (/= curr_scale 7.5))
	(progn
	  (cond
	    ((= cn7_dwgunit 1) (command "._zoom" "_c" zxp_cenpt (strcat "1000/" (rtos curr_scale 2 0) "xp")))
	    ((= cn7_dwgunit 100) (command "._zoom" "_c" zxp_cenpt (strcat "10/" (rtos curr_scale 2 0) "xp")))
	    ((= cn7_dwgunit 1000) (command "._zoom" "_c" zxp_cenpt (strcat "1/" (rtos curr_scale 2 0) "xp")))
	  )
	  (if (/= "14" (substr (getvar "acadver") 1 2)) (cn7_zxp_wishlock))
	)
	(progn
	  (cond
	    ((= curr_scale 1.25)
	     (cond
	       ((= cn7_dwgunit 1) (command "._zoom" "_c" zxp_cenpt "100000/125xp"))
	       ((= cn7_dwgunit 100) (command "._zoom" "_c" zxp_cenpt "1000/125xp"))
	       ((= cn7_dwgunit 1000) (command "._zoom" "_c" zxp_cenpt "100/125xp"))
	     ))
	    ((= curr_scale 1.5)
	     (cond
	       ((= cn7_dwgunit 1) (command "._zoom" "_c" zxp_cenpt "10000/15xp"))
	       ((= cn7_dwgunit 100) (command "._zoom" "_c" zxp_cenpt "100/15xp"))
	       ((= cn7_dwgunit 1000) (command "._zoom" "_c" zxp_cenpt "10/15xp"))
	     ))
	    ((= curr_scale 2.5)
	     (cond
	       ((= cn7_dwgunit 1) (command "._zoom" "_c" zxp_cenpt "10000/25xp"))
	       ((= cn7_dwgunit 100) (command "._zoom" "_c" zxp_cenpt "100/25xp"))
	       ((= cn7_dwgunit 1000) (command "._zoom" "_c" zxp_cenpt "10/25xp"))
	     ))
	    ((= curr_scale 7.5)
	     (cond
	       ((= cn7_dwgunit 1) (command "._zoom" "_c" zxp_cenpt "10000/75xp"))
	       ((= cn7_dwgunit 100) (command "._zoom" "_c" zxp_cenpt "100/75xp"))
	       ((= cn7_dwgunit 1000) (command "._zoom" "_c" zxp_cenpt "10/75xp"))
	     ))
	    ((= curr_scale 12.5)
	     (cond
	       ((= cn7_dwgunit 1) (command "._zoom" "_c" zxp_cenpt "10000/125xp"))
	       ((= cn7_dwgunit 100) (command "._zoom" "_c" zxp_cenpt "100/125xp"))
	       ((= cn7_dwgunit 1000) (command "._zoom" "_c" zxp_cenpt "10/125xp"))
	     ))
	  )
	  (if (/= "14" (substr (getvar "acadver") 1 2)) (cn7_zxp_wishlock))
	)
      )
    )
    (exit)
  )
)

(defun cn7_vwpesc_veryget ()
  (setq cn7_vwpesc $value)
  (if (not (distof cn7_vwpesc))
    (progn
      (cn7_alert_ok
	    "Entrada Inválida!"
	    "Digite um valor"
	    "Numérico...")
    )
    (progn
      (setq cn7_dzin (getvar "dimzin"))
      (setvar "dimzin" 1)
      (setq cn7_listmemb "n" alert_resp nil)
      (setq cn7_scalist
	 (list
	   "1.000" "10.000" "100.000" "1000.000" "10000.000" "100000.000" "1000000.000"
	   "1.250" "12.500" "125.000" "1250.000" "12500.000" "125000.000"
	   "1.500" "15.000" "150.000" "1500.000" "15000.000" "150000.000"
	   "2.000" "20.000" "200.000" "2000.000" "20000.000" "200000.000"
	   "2.500" "25.000" "250.000" "2500.000" "25000.000" "250000.000"
	   "3.000" "30.000" "300.000" "3000.000" "30000.000" "300000.000"
	   "4.000" "40.000" "400.000" "4000.000" "40000.000" "400000.000"
	   "5.000" "50.000" "500.000" "5000.000" "50000.000" "500000.000"
	   "7.500" "75.000" "750.000" "7500.000" "75000.000" "750000.000"))
      (setq cn7_vpscl_verify (distof cn7_vwpesc))
      (foreach n cn7_scalist
	(if (= (rtos cn7_vpscl_verify 2 3) n) (setq cn7_listmemb "s"))
      )
      (if (= cn7_listmemb "n")
	;se a escala da janela é irregular
	(progn
	  (cn7_alert_yes_no
	    "Esta escala não é padrão!"
	    (strcat "Escala atual = 1:" cn7_vwpesc)
	    "Deseja continuar mesmo assim?")
	  (if (= "no" alert_resp)
	    (done_dialog 0)
	    (progn
	      (setq curr_scale (distof cn7_vwpesc))
	    )
	  )
	);
	;se a escala da janela é regular
	(progn
	  (setq curr_scale (distof cn7_vwpesc))
	  )
	)
      )
    )
  )




;pergunta se quer trancar a viewport ativa depois do zoom/xp
(defun cn7_zxp_wishlock ()
  (cn7_alert_yes_no
    " "
    "Você gostaria de trancar essa Viewport?"
    " ")
  (if (= alert_resp "yes")
    (progn
      (setq cn7_curvp_list (assoc (getvar "cvport") (setq all_views (vports))))
      (command "._pspace")
	;;;      (setq ename (ssname (ssget "c" (nth 1 cn7_curvp_list) (nth 1 cn7_curvp_list)) 0))
      (setq cn7_cvp_list (entget (ssname (ssget "c" (nth 1 cn7_curvp_list) (nth 1 cn7_curvp_list)) 0)))
      (command "._mview" "_l" "_on" "_c" (nth 1 cn7_curvp_list) (nth 1 cn7_curvp_list) "")
      (command "._mspace")
    )
  )
)


;verifica se está no Paper e na viewport
(defun cn7_very_ispaper ()
  (if (= 1 (getvar "tilemode"))
    (progn
      (cn7_alert_ok
	"Você está operando no Model Space."
	"Esta operação não é permitida aqui!"
	"Mude para o Paper Space...")
      (exit)
    )
    (progn
      (if (= (getvar "cvport") 1) (cn7_cur_vport))
    )
  )
)

;torna corrente a vport selecionada
(defun cn7_cur_vport ()
  (prompt "\nSelecione a Viewport cuja escala deseja alterar...")
  (setq cn7_curvp (entsel))
  (if
    (and
      (/= "VIEWPORT" (setq cur_vp (strcase (cdr (assoc 0 (entget (car cn7_curvp)))))))
      (/= "LWPOLYLINE" (setq cur_vp (strcase (cdr (assoc 0 (entget (car cn7_curvp)))))))
    )
    (progn
      (alert "A entidade selecionada não é uma Viewport,\nou é uma Viewport Irregular!\n\nNesse caso, ative a Viewport\npara alterar a sua escala!...")
      (cn7_cur_vport)
    )
    (command "._mspace" "._cvport" (cdr (assoc 69 (entget (car cn7_curvp)))))
  )	
)


(defun cn7_verylocked  ()
  (setq cn7_curvp_list (assoc (getvar "cvport") (setq all_views (vports))))
  (command "._pspace")
  (cond
    ((/= nil (ssget "c" (nth 1 cn7_curvp_list) (nth 1 cn7_curvp_list)'((0 . "VIEWPORT"))))
     (setq cn7_cvp_list (entget (ssname (ssget "c" (nth 1 cn7_curvp_list) (nth 1 cn7_curvp_list)'((0 . "VIEWPORT"))) 0))))
    ((/= nil (ssget "c" (nth 1 cn7_curvp_list) (nth 1 cn7_curvp_list)'((0 . "VIEWPORT"))))
     (setq cn7_cvp_list (entget (ssname (ssget "c" (nth 1 cn7_curvp_list) (nth 1 cn7_curvp_list)'((0 . "LWPOLYLINE"))) 0))))
  )
  (if (and (> (cdr (assoc 90 cn7_cvp_list)) 49000) (< (cdr (assoc 90 cn7_cvp_list)) 50000))
    (progn
      (cn7_alert_yes_no
	"A Viewport está trancada!"
	"Deseja destrancá-la e alterar"
	"sua escala de visualização?"
      )
      (if (= alert_resp "no")
	(exit)
	(progn
	  (command "._mview" "_l" "_off" "_c" (nth 1 cn7_curvp_list) (nth 1 cn7_curvp_list) "")
	  (command "._mspace")
	)
      )
    )
    (command "._mspace")
  )
)
  
	
  

;************************************************************************
;DEFINE UMA NOVA VIEWPORT
;************************************************************************
(defun c:vwp ()
  (cn7_init)
  (guarda '("blipmode" "cecolor" "celtype" "clayer" "cmdecho" "orthomode"
          "textstyle" "luprec" "osmode" "dimzin"))
  (cn7_vp_create)
  (devolve)
  (princ)
)

(defun cn7_vp_create ()
  (if (= 1 (getvar "tilemode"))
    (progn
      (cn7_alert_ok
	"Você está operando no Model Space."
	"Esta operação não é permitida aqui!"
	"Mude para o Paper Space...")
      (exit)
    )
  )
  (command "._pspace")
  (initget 128)
  (setq pt1 (getpoint "\nObjeto/Marque o primeiro ponto da viewport..."))
    (cond
      ((= 'LIST (type pt1))
       (setq pt2 (getcorner pt1 "\nMarque o Segundo ponto da viewport..."))
       (if (tblsearch "layer" "viewport") (command "._vplayer" "_t" "viewport" "" ""))
       (cn7_verylayer "VIEWPORT" 7)
       (command "._layer" "_p" "_n" "viewport" "")
       (setq osmo (getvar "osmode"))
       (setvar "osmode" 0)
       (command"._mview" pt1 pt2 "._mspace")
       (setvar "osmode" osmo)
       (cn7_vp_zxp)
      )
      ((= 'STR  (type pt1))
       (cond
	 ((= "O" (strcase pt1))
	  (prompt "\nSelecione o objeto a se tornar uma viewport...")
	  (setq cn7_vp_objeto (entsel))
	  (command "._mview" "_object" cn7_vp_objeto "._mspace")
	  (cn7_vp_zxp)
	  
	 )
	 (t (prompt "\nOpção inválida! Digite 'O' ou marque o primeiro ponto...")
	  (cn7_vp_create)
	 )
       )
      )
   )
)


;**********************************************************
;********** Operações com Layers nas Viewports ************
;**********************************************************
(defun c:vfz (/ p x OorF)
  (if (not (and (= 0 (getvar "tilemode")) (/= 1 (getvar "cvport"))))
    (progn
      (alert "Comando válido\nsomente em uma Viewport!\nOperação cancelada!!")
      (exit)))
  (setq x (entsel "\nSelecione o objeto cujo layer deve ser congelado "))
  (setq vfz_p (cdr (assoc 8 (entget (car x)))))
  (if (/= vfz_p (getvar "clayer"))
    (command "._vplayer" "_freeze" vfz_p "" "")
    (progn
      (alert "Impossível Congelar o Layer Atual...
      		\nSelecione uma Entidade para tornar seu Layer Corrente
      		\ne Congelar o Layer Desejado...")
      (setq x2 (entsel))
      (setq p2 (cdr (assoc 8 (entget (car x2)))))
      (command "._layer" "_s" p2 "")
      (command "._vplayer" "_freeze" vfz_p "" "")
    )
  )
  (princ)
)


(defun c:vuf ()
  (if (/= nil vfz_p)
    (command "._vplayer" "_thaw" vfz_p "" "")
    (prompt "\nNenhum layer congelado pelo STACAD recentemente...")
  )
  (princ)
)

(defun c:v2 () (command "._vplayer" "_t" "*" "" "")(princ))

(defun c:viso (/ p x OorF)
  (setq x (entsel "\nSelecione o objeto cujo layer deve ser isolado.."))
  (setq p (cdr (assoc 8 (entget (car x)))))
  (command "._layer" "_s" p "")
  (command "vplayer" "_f" "*" "" "_t" p "" "")
  (princ)
)


;cnp_04

;******************************************************************************
;******************************************************************************
;comando de setagem de cores
;******************************************************************************
;******************************************************************************
(defun C:c0  () (setvar "cecolor" "bylayer")(princ))
(defun c:c1  () (setvar "cecolor" "1") (command "._line")(princ))
(defun c:c2  () (setvar "cecolor" "2") (command "._line")(princ))
(defun c:c3  () (setvar "cecolor" "3") (command "._line")(princ))
(defun c:c4  () (setvar "cecolor" "4") (command "._line")(princ))
(defun c:c5  () (setvar "cecolor" "5") (command "._line")(princ))
(defun c:c6  () (setvar "cecolor" "6") (command "._line")(princ))
(defun c:c7  () (setvar "cecolor" "7") (command "._line")(princ))

;iguala cor
(defun c:eqcolor ()
  (setq x (entsel "\nSelecione a Entidade Base"))
  (setq p (cdr (assoc 62 (entget (car x)))))
  (prompt (strcat "\nCor base :" (rtos p 2 0)))
  (prompt "\nSelecione as entidades para mudanca")
  (setq s1 (ssget))
  (command "._chprop" s1 "" "_c" p "")
  (princ)
)

;Mudar cor para
(defun c:tocolor ()
  (prompt "\nSelecione as entidades para mudanca")
  (setq s1 (ssget))
  (command "._chprop" s1 "" "_c" (acad_colordlg 7) "")
  (princ)
)

;Troca cor
(defun c:trcolor () (cn9_xchgcolor) (princ))


(defun cn9_xchgcolor ()
  (setq dcl_id (load_dialog (strcat cnp_root "/lisp/cadnorma.dcl")))
  (if (not (new_dialog "cn9_trcolor" dcl_id)) (exit))
  (if (/= nil trcolor_from)
    (progn
      (start_image "trcolor_from_col")
      (fill_image  0  0
	(dimx_tile "trcolor_from_col")
	(dimy_tile "trcolor_from_col")
	trcolor_from
      )
      (end_image)
      (cond
	((= 0 trcolor_from) (set_tile "trcolor_txt_from" (strcat "Cor selecionada: " "byblock")))
	((= 256 trcolor_from) (set_tile "trcolor_txt_from" (strcat "Cor selecionada: " "bylayer")))
	(t (set_tile "trcolor_txt_from" (strcat "Cor selecionada: " (rtos trcolor_from 2 0))))
      )
    )
  )
  (if (/= nil trcolor_to)
    (progn
      (start_image "trcolor_to_col")
      (fill_image  0  0
	(dimx_tile "trcolor_to_col")
	(dimy_tile "trcolor_to_col")
	trcolor_to
      )
      (end_image)
      (cond
	((= 0 trcolor_to) (set_tile "trcolor_txt_to" (strcat "Cor selecionada: " "byblock")))
	((= 256 trcolor_to) (set_tile "trcolor_txt_to" (strcat "Cor selecionada: " "bylayer")))
	(t (set_tile "trcolor_txt_to" (strcat "Cor selecionada: " (rtos trcolor_to 2 0))))
      )
    )
  )
  (action_tile "cancel" "(done_dialog 0)")
  (action_tile "accept" "(done_dialog 1)")
  (action_tile "trcolor_from_sel" "(done_dialog 2)")
  (action_tile "trcolor_from_pick" "(done_dialog 3)")
  (action_tile "trcolor_to_sel" "(done_dialog 4)")
  (action_tile "trcolor_to_pick" "(done_dialog 5)")
  (setq cn9_trcolor_dcl (start_dialog))
  (unload_dialog dcl_id)
  (if (= cn9_trcolor_dcl 0) (exit))
  (if (= cn9_trcolor_dcl 1) (cn9_trocacor))
  (if (= cn9_trcolor_dcl 2) (cn9_trcolor_from_sel))
  (if (= cn9_trcolor_dcl 3) (cn9_trcolor_from_pick))
  (if (= cn9_trcolor_dcl 4) (cn9_trcolor_to_sel))
  (if (= cn9_trcolor_dcl 5) (cn9_trcolor_to_pick))
)

(defun cn9_trcolor_from_sel ()
  (setq trcolor_from (acad_colordlg 7))
  (cn9_xchgcolor)
)

(defun cn9_trcolor_from_pick ()
  (setq x (entsel "\nSelecione uma entidade para cor base... "))
  (setq trcolor_from (cdr (assoc 62 (entget (car x)))))
  (if (= nil trcolor_from) (setq trcolor_from 256))
  (cn9_xchgcolor)
)

(defun cn9_trcolor_to_sel ()
  (done_dialog 2)
  (setq trcolor_to (acad_colordlg 7))
  (cn9_xchgcolor)
)

(defun cn9_trcolor_to_pick ()
  (done_dialog 2)
  (setq x (entsel "\nSelecione uma entidade para cor destino... "))
  (setq trcolor_to (cdr (assoc 62 (entget (car x)))))
  (if (= nil trcolor_to) (setq trcolor_to 256))
  (cn9_xchgcolor)
)

(defun cn9_trocacor ()
  (prompt "\nselecione as entidades para tocar a cor...")
  (setq s1 (ssget)
	s1_n (sslength s1)
	counter 0
	new_list (cons 62 trcolor_to)
  )
  (if (/= 256 trcolor_from)
    (repeat s1_n
      (setq ent (entget (ssname s1 counter)))
      (if (= (cdr (assoc 62 ent)) trcolor_from)
	(cond
	  ((= 0 trcolor_to) (command "._chprop" (ssname s1 counter) "" "_c" "byblock" ""))
	  ((= 256 trcolor_to) (command "._chprop" (ssname s1 counter) "" "_c" "bylayer" ""))
	  (t (command "._chprop" (ssname s1 counter) "" "_c" trcolor_to ""))
        )
      )
      (setq counter (1+ counter))
    )
    (repeat s1_n
      (setq ent (entget (ssname s1 counter)))
      (if (not (cdr (assoc 62 ent)))
	(cond
	  ((= 0 trcolor_to) (command "._chprop" (ssname s1 counter) "" "_c" "byblock" ""))
	  ((= 256 trcolor_to) (command "._chprop" (ssname s1 counter) "" "_c" "bylayer" ""))
	  (t (command "._chprop" (ssname s1 counter) "" "_c" trcolor_to ""))
        )
      )
      (setq counter (1+ counter))
    )
  )
)

;cnp_05


;*************************************************************************************************
;*************************************************************************************************
;*************************************  Comandos de Layers ***************************************
;*************************************************************************************************
;*************************************************************************************************
;*************************************************************************************************
;*************************************************************************************************

;layers auxiliares - tornar current
(defun c:01  () (command "._layer" "_m" "AUX_01" "_c" "1" "" "" "._line") (princ))
(defun c:02  () (command "._layer" "_m" "AUX_02" "_c" "2" "" "" "._line") (princ))
(defun c:03  () (command "._layer" "_m" "AUX_03" "_c" "3" "" "" "._line") (princ))
(defun c:04  () (command "._layer" "_m" "AUX_04" "_c" "4" "" "" "._line") (princ))
(defun c:05  () (command "._layer" "_m" "AUX_05" "_c" "5" "" "" "._line") (princ))
(defun c:06  () (command "._layer" "_m" "AUX_06" "_c" "6" "" "" "._line") (princ))
(defun c:07  () (command "._layer" "_m" "AUX_07" "_c" "7" "" "" "._line") (princ))
(defun c:08  () (command "._layer" "_m" "AUX_08" "_c" "8" "" "" "._line") (princ))

;layers auxiliares - mudar para
(defun c:p1 () (tolay "01") (princ))
(defun c:p2 () (tolay "02") (princ))
(defun c:p3 () (tolay "03") (princ))
(defun c:p4 () (tolay "04") (princ))
(defun c:p5 () (tolay "05") (princ))
(defun c:p6 () (tolay "06") (princ))
(defun c:p7 () (tolay "07") (princ))
(defun c:p8 () (tolay "08") (princ))
  
(defun tolay (lay)
  (setq laymo (getvar "clayer"))
  (setq new-layer (strcat "AUX_" lay))
  (prompt (strcat "\nSelecione os objetos a serem transferidos para o layer <" new-layer ">..."))
  (setq s1 (ssget))
  (if (tblsearch "layer" new-layer)
    (command "._chprop" "_p" "" "_la" new-layer "");case T
    (progn
      (if (= lay "01") (command "._layer" "_m" new-layer "_c" "1" "" "" "._chprop" "_p" "" "_la" new-layer ""))
      (if (= lay "02") (command "._layer" "_m" new-layer "_c" "2" "" "" "._chprop" "_p" "" "_la" new-layer ""))
      (if (= lay "03") (command "._layer" "_m" new-layer "_c" "3" "" "" "._chprop" "_p" "" "_la" new-layer ""))
      (if (= lay "04") (command "._layer" "_m" new-layer "_c" "4" "" "" "._chprop" "_p" "" "_la" new-layer ""))
      (if (= lay "05") (command "._layer" "_m" new-layer "_c" "5" "" "" "._chprop" "_p" "" "_la" new-layer ""))
      (if (= lay "06") (command "._layer" "_m" new-layer "_c" "6" "" "" "._chprop" "_p" "" "_la" new-layer ""))
      (if (= lay "07") (command "._layer" "_m" new-layer "_c" "7" "" "" "._chprop" "_p" "" "_la" new-layer ""))
      (if (= lay "08") (command "._layer" "_m" new-layer "_c" "8" "" "" "._chprop" "_p" "" "_la" new-layer ""))
    );progn case F
  );if
  (setvar "clayer" laymo)
)

;pick layer (antigo change layer)
(defun c:pkl (/ p x s1)
  (setq x (entsel "\nSelecione a Entidade Base"))
  (setq p (cdr (assoc 8(entget (car x)))))
  (prompt "\nLayer base :")
  (prompt p)
  (prompt "\nSelecione as entidades para mudanca")
  (setq s1 (ssget))
  (command "._chprop" s1 "" "_la" p "")
  (princ)
)

;torna currente o layer de uma entidade selecionada
(defun c:cur (/ p x s1)
  (setq x (entsel "\nSelecione a cujo layer deve ser o atual..."))
  (setq p (cdr (assoc 8(entget (car x)))))
  (setvar "clayer" p)
  (princ)
)


;muda os objetos selecionados para o layer current
(defun C:tcr ()
  (setq a (getvar "clayer"))
  (prompt "\nSelecione as entidades para mudanca")
  (ssget)
  (command "._chprop" "_p" "" "_la" a "")
  (princ)
)

;Congela o layer de uma entidade selecionada
(defun c:fz (/ p x OorF)
  (while (/= nil (setq x (entsel "\nSelecione o objeto cujo layer deve ser congelado... ")))
    (setq fz_p (cdr (assoc 8 (entget (car x)))))
    (if (/= fz_p (getvar "clayer"))
      (command "._layer" "_freeze" fz_p "")
      (progn
	(alert "Impossível Congelar o Layer Atual...
	\nSelecione uma Entidade para tornar seu Layer Corrente
	\ne Congelar o Layer Desejado...")
	(setq x2 (entsel))
	(setq p2 (cdr (assoc 8 (entget (car x2)))))
	(command "._layer" "_s" p2 "")
	(command "._layer" "_freeze" fz_p "")
      )
    )
  )
  (princ)
)


;desliga o layer selecionado
(defun c:ofl (/ p x OorF)
  (while (/= nil (setq x (entsel "\nSelecione o objeto cujo layer deve ser desligado... ")))
    (setq fz_p (cdr (assoc 8 (entget (car x)))))
    (if (/= fz_p (getvar "clayer"))
      (command "._layer" "_off" fz_p "")
      (progn
	(Initget 1 "Sim Nao")
	(setq resp (getkword "\nDeseja realmente desligar o layer atual? <S/N>... "))
	(if (= resp "Nao")
	  (progn
	    (prompt "Selecione uma entidade para tornar seu layer corrente... ")
	    (setq x2 (entsel))
	    (setq p2 (cdr (assoc 8 (entget (car x2)))))
	    (command "._layer" "_s" p2 "")
	    (command "._layer" "_off" fz_p "")
	    )
	  (progn
	    (command "._layer" "_off" fz_p "_y" "")
	    (alert "Atenção!\nLayer atual desligado!!!")
	    )
	);if
      )
    )
  )
  (princ)
)

;Tranca o layer de um conjunto de entidades selecionadas
(defun c:lkl (/ p x OorF)
  (prompt "\nSelecione os objetos cujos layers devem ser trancados <lock>")
  (setq s1 (ssget)
	s1_len (sslength s1)
	counter 0
	lay_list (list)
  )
  (command "._layer")
  (repeat s1_len
    (setq e1_lay (cdr (assoc 8 (entget (ssname s1 counter)))))
    (command  "_lo" e1_lay)
    (setq counter (1+ counter))
  )
  (command "")
  (princ)
)

;Destranca o layer de um conjunto de entidades selecionadas
(defun c:ulk (/ p x OorF)
  (prompt "\nSelecione os objetos cujos layers devem ser destrancados <unlock>")
  (setq s1 (ssget)
	s1_len (sslength s1)
	counter 0
	lay_list (list)
  )
  (command "._layer")
  (repeat s1_len
    (setq e1_lay (cdr (assoc 8 (entget (ssname s1 counter)))))
    (command  "_unlock" e1_lay)
    (setq counter (1+ counter))
  )
  (command "")
  (princ)
)


;descongela todos os layers
(defun c:twl () (command "._layer" "_t" "*" "") (princ))
(defun c:2 () (command "._layer" "_t" "*" "") (princ))


;liga todos os layers
(defun c:onl () (command "._layer" "_on" "*" "") (princ))

;destranca todos os layers
(defun c:ulka () (command "._layer" "_unlock" "*" "") (princ))


;isolate by freeze
(defun c:isf ()
  (setq echo (getvar "CMDECHO"))
  (setvar "CMDECHO" 0)
  (prompt "\nSelecione os layers a serem isolados...")
  (setq isolay_keep (ssget))
  (if (null isolay_keep)
    (while (null isolay_keep)
      (princ "\nTente novamente ou pressione <ESC> para sair ")
      (prompt "\nSelecione os layers a serem isolados...")
      (setq isolay_keep (ssget))
    )
  )
  (setq isolay_list (list "")
	counter 0
	isolay_currlay (cdr (assoc 8 (entget (ssname isolay_keep 0))))
	isolay_currcol (cdr (assoc 62 (tblsearch "layer" isolay_currlay)))
  )
  (while (/= nil (setq ent (ssname isolay_keep counter)))
    (setq isolay_list (append isolay_list (list (cdr (assoc 8 (entget ent))))))
    (setq counter (1+ counter))
  )
  (setq isolay_list (cdr isolay_list))
  (if (not (member (getvar "clayer") isolay_list))
    (setvar "clayer" (nth 0 isolay_list))
  )
  (command "._layer" "_freeze" "*")
  (foreach n isolay_list
    (command "_thaw" n)
  )
  (command "")  
  (setvar "CMDECHO" echo)
  (princ)
)


;isolate by off
(defun c:iso ()
  (setq echo (getvar "CMDECHO"))
  (setvar "CMDECHO" 0)
  (prompt "\nSelecione os layers a serem isolados...")
  (setq isolay_keep (ssget))
  (if (null isolay_keep)
    (while (null isolay_keep)
      (princ "\nTente novamente ou pressione <ESC> para sair ")
      (prompt "\nSelecione os layers a serem isolados...")
      (setq isolay_keep (ssget))
    )
  )
  (setq isolay_list (list "")
	counter 0
	isolay_currlay (cdr (assoc 8 (entget (ssname isolay_keep 0))))
	isolay_currcol (cdr (assoc 62 (tblsearch "layer" isolay_currlay)))
  )
  (while (/= nil (setq ent (ssname isolay_keep counter)))
    (setq isolay_list (append isolay_list (list (cdr (assoc 8 (entget ent))))))
    (setq counter (1+ counter))
  )
  (setq isolay_list (cdr isolay_list))
  (command "._layer" "_off" "*" "_y")
  (foreach n isolay_list
    (command "_on" n)
  )
  (command "")  
  (setvar "CMDECHO" echo)
  (princ)
)


;isolate by lock
(defun c:isk ()
  (setq echo (getvar "CMDECHO"))
  (setvar "CMDECHO" 0)
  (prompt "\nSelecione os layers a serem isolados...")
  (setq isolay_keep (ssget))
  (if (null isolay_keep)
    (while (null isolay_keep)
      (princ "\nTente novamente ou pressione <ESC> para sair ")
      (prompt "\nSelecione os layers a serem isolados...")
      (setq isolay_keep (ssget))
    )
  )
  (setq isolay_list (list "")
	counter 0
	isolay_currlay (cdr (assoc 8 (entget (ssname isolay_keep 0))))
	isolay_currcol (cdr (assoc 62 (tblsearch "layer" isolay_currlay)))
  )
  (while (/= nil (setq ent (ssname isolay_keep counter)))
    (setq isolay_list (append isolay_list (list (cdr (assoc 8 (entget ent))))))
    (setq counter (1+ counter))
  )
  (setq isolay_list (cdr isolay_list))
  (command "._layer" "_lock" "*" "")
  (foreach n isolay_list
    (command "._layer" "_unlock" n "")
  )
  (setvar "CMDECHO" echo)
  (princ)
)

(defun c:lac ()
  (setq dcl_id (load_dialog (strcat cnp_root "/lisp/cadnorma.dcl")))
  (if (not (new_dialog "cn7_laycon" dcl_id)) (exit))
  ;interpreta os valores iniciais
  (cond
    ((= 0 (getvar "useri5"))
     (set_tile "allay_text_cadnorma" "1")
     (set_tile "allay_text_custom" "1")
     (setq cdn_txt 1 cus_txt 1))    
    ((= 1 (getvar "useri5"))
     (set_tile "allay_text_cadnorma" "1")
     (set_tile "allay_text_custom" "0")
     (setq cdn_txt 1 cus_txt 0))
    ((= 2 (getvar "useri5"))
     (set_tile "allay_text_cadnorma" "0")
     (set_tile "allay_text_custom" "1")
     (setq cdn_txt 0 cus_txt 1))
    ((= 3 (getvar "useri5"))
     (set_tile "allay_text_cadnorma" "0")
     (set_tile "allay_text_custom" "0")
     (setq cdn_txt 0 cus_txt 0))
  )
  (cond
    ((= 0 (getvar "useri4"))
     (set_tile "allay_dim_cadnorma" "1")
     (set_tile "allay_dim_custom" "1")
     (setq cdn_dim 1 cus_dim 1))
    ((= 1 (getvar "useri4"))
     (set_tile "allay_dim_cadnorma" "1")
     (set_tile "allay_dim_custom" "0")
     (setq cdn_dim 1 cus_dim 0))
    ((= 2 (getvar "useri4"))
     (set_tile "allay_dim_cadnorma" "0")
     (set_tile "allay_dim_custom" "1")
     (setq cdn_dim 0 cus_dim 1))
    ((= 3 (getvar "useri4"))
     (set_tile "allay_dim_cadnorma" "0")
     (set_tile "allay_dim_custom" "0")
     (setq cdn_dim 0 cus_dim 0))
  )
  ;ações dos toggles
  (action_tile "allay_text_cadnorma" "(setq cdn_txt (fix (distof $value)))")
  (action_tile "allay_text_custom" "(setq cus_txt (fix (distof $value)))")
  (action_tile "allay_dim_cadnorma" "(setq cdn_dim (fix (distof $value)))")
  (action_tile "allay_dim_custom" "(setq cus_dim (fix (distof $value)))")
  (action_tile "cancel" "(done_dialog 0)")
  (action_tile "accept" "(done_dialog 1)")
  (setq laycon_dcl (start_dialog))
  (unload_dialog dcl_id)
  (if (= 1 laycon_dcl) (cn7_lac_ok))
  (princ)
)

;layer control - botão OK
(defun cn7_lac_ok ()
  (cond
    ((and (= cdn_txt 1) (= cus_txt 1)) (setvar "useri5" 0))
    ((and (= cdn_txt 1) (= cus_txt 0)) (setvar "useri5" 1))
    ((and (= cdn_txt 0) (= cus_txt 1)) (setvar "useri5" 2))
    ((and (= cdn_txt 0) (= cus_txt 0)) (setvar "useri5" 3))
  )
  (cond
    ((and (= cdn_dim 1) (= cus_dim 1)) (setvar "useri4" 0))
    ((and (= cdn_dim 1) (= cus_dim 0)) (setvar "useri4" 1))
    ((and (= cdn_dim 0) (= cus_dim 1)) (setvar "useri4" 2))
    ((and (= cdn_dim 0) (= cus_dim 0)) (setvar "useri4" 3))
  )
)

;inserção de layers
(defun c:lay ()
  (setq allayer_projlist
	 (list"Geral" "Arquitetura" "Paisagismo"
	      "Urbanismo" "Elétrica" "Telefone"
	      "Rede Lógica" "Água" "Esgoto"
	      "Incêndio" "Aterramento" "Ar Condicionado"
	      "Concreto" "Metálica" "Gás"
	      "Automação" "Alarme" "CFTV"
	      "Som" "Topografia" "User_01"
	      "User_02" "User_03"))
  (setq dcl_id (load_dialog (strcat cnp_root "/lisp/cadnorma.dcl")))
  (if (not (new_dialog "cn7_layins" dcl_id)) (exit))
  ;preenche a lista de projetos disponíveis
  (start_list "allayer_modelos")
  (mapcar 'add_list allayer_projlist)
  (end_list)
  (action_tile "allayer_modelos" "(setq allayer_project $value)")
  (action_tile "cancel" "(done_dialog 0)")
  (action_tile "accept" "(done_dialog 1)")
  (setq layins_dcl (start_dialog))
  (unload_dialog dcl_id)
  (if (= 1 layins_dcl) (cn7_dwg_allayer2))
  (princ)
)

(defun cn7_dwg_allayer2 ()
    (cond
      ((= "0" allayer_project)
       (command "._insert" (strcat cnp_root "/modelos/cadnorma_geral") "0,0" "" "" "" "._erase" (entlast) ""  "._purge" "_b" "cadnorma_geral" "n"))
      ((= "1" allayer_project)
       (command "._insert" (strcat cnp_root "/modelos/cadnorma_arquitetura") "0,0" "" "" "" "._erase" (entlast) ""  "._purge" "_b" "cadnorma_arquitetura" "n"))
      ((= "2" allayer_project)
       (command "._insert" (strcat cnp_root "/modelos/cadnorma_paisagismo") "0,0" "" "" "" "._erase" (entlast) ""  "._purge" "_b" "cadnorma_paisagismo" "n"))
      ((= "3" allayer_project)
       (command "._insert" (strcat cnp_root "/modelos/cadnorma_urbanismo") "0,0" "" "" "" "._erase" (entlast) ""  "._purge" "_b" "cadnorma_urbanismo" "n"))
      ((= "4" allayer_project)
       (command "._insert" (strcat cnp_root "/modelos/cadnorma_elétrica") "0,0" "" "" "" "._erase" (entlast) ""  "._purge" "_b" "cadnorma_elétrica" "n"))
      ((= "5" allayer_project)
       (command "._insert" (strcat cnp_root "/modelos/cadnorma_telefone") "0,0" "" "" "" "._erase" (entlast) ""  "._purge" "_b" "cadnorma_telefone" "n"))
      ((= "6" allayer_project)
       (command "._insert" (strcat cnp_root "/modelos/cadnorma_lógica") "0,0" "" "" "" "._erase" (entlast) ""  "._purge" "_b" "cadnorma_lógica" "n"))
      ((= "7" allayer_project)
       (command "._insert" (strcat cnp_root "/modelos/cadnorma_água") "0,0" "" "" "" "._erase" (entlast) ""  "._purge" "_b" "cadnorma_água" "n"))
      ((= "8" allayer_project)
       (command "insert" (strcat cnp_root "/modelos/cadnorma_esgoto") "0,0" "" "" "" "._erase" (entlast) ""  "._purge" "_b" "cadnorma_esgoto" "n"))
      ((= "9" allayer_project)
       (command "._insert" (strcat cnp_root "/modelos/cadnorma_incêndio") "0,0" "" "" "" "._erase" (entlast) ""  "._purge" "_b" "cadnorma_incêndio" "n"))
      ((= "10" allayer_project)
       (command "._insert" (strcat cnp_root "/modelos/cadnorma_aterramento") "0,0" "" "" "" "._erase" (entlast) ""  "._purge" "_b" "cadnorma_aterramento" "n"))
      ((= "11" allayer_project)
       (command "._insert" (strcat cnp_root "/modelos/cadnorma_ar_condicionado") "0,0" "" "" "" "._erase" (entlast) ""  "._purge" "_b" "cadnorma_ar_condicionado" "n"))
      ((= "12" allayer_project)
       (command "._insert" (strcat cnp_root "/modelos/cadnorma_concreto") "0,0" "" "" "" "._erase" (entlast) ""  "._purge" "_b" "cadnorma_concreto" "n"))
      ((= "13" allayer_project)
       (command "._insert" (strcat cnp_root "/modelos/cadnorma_metálica") "0,0" "" "" "" "._erase" (entlast) ""  "._purge" "_b" "cadnorma_metálica" "n"))
      ((= "14" allayer_project)
       (command "._insert" (strcat cnp_root "/modelos/cadnorma_gás") "0,0" "" "" "" "._erase" (entlast) ""  "._purge" "_b" "cadnorma_gás" "n"))
      ((= "15" allayer_project)
       (command "._insert" (strcat cnp_root "/modelos/cadnorma_automação") "0,0" "" "" "" "._erase" (entlast) ""  "._purge" "_b" "cadnorma_automação" "n"))
      ((= "16" allayer_project)
       (command "._insert" (strcat cnp_root "/modelos/cadnorma_alarme") "0,0" "" "" "" "._erase" (entlast) ""  "._purge" "_b" "cadnorma_alarme" "n"))
      ((= "17" allayer_project)
       (command "._insert" (strcat cnp_root "/modelos/cadnorma_cftv") "0,0" "" "" "" "._erase" (entlast) ""  "._purge" "_b" "cadnorma_cftv" "n"))
      ((= "18" allayer_project)
       (command "._insert" (strcat cnp_root "/modelos/cadnorma_som") "0,0" "" "" "" "._erase" (entlast) ""  "._purge" "_b" "cadnorma_som" "n"))
      ((= "19" allayer_project)
       (command "._insert" (strcat cnp_root "/modelos/cadnorma_topografia") "0,0" "" "" "" "._erase" (entlast) ""  "._purge" "_b" "cadnorma_topografia" "n"))
      ((= "20" allayer_project)
       (command "._insert" (strcat cnp_root "/modelos/cadnorma_user01") "0,0" "" "" "" "._erase" (entlast) ""  "._purge" "_b" "cadnorma_user01" "n"))
      ((= "21" allayer_project)
       (command "._insert" (strcat cnp_root "/modelos/cadnorma_user02") "0,0" "" "" "" "._erase" (entlast) ""  "._purge" "_b" "cadnorma_user02" "n"))
      ((= "22" allayer_project)
       (command "._insert" (strcat cnp_root "/modelos/cadnorma_user03") "0,0" "" "" "" "._erase" (entlast) ""  "._purge" "_b" "cadnorma_user03" "n"))
      (t (alert "Nenhum projeto Selecionado!"))
    )
)

;cnp_06



;******************************************************************************
;******************************************************************************
;Linetypes Especiais - Criar
;******************************************************************************
;******************************************************************************

;grupo I - linhas gráficas
(defun c:lint  () (cn7_ltype "INTERRUP") (princ))
(defun c:lhd1  () (cn7_ltype "HIDDEN") (princ))
(defun c:lhd2  () (cn7_ltype "HIDDEN2") (princ))
(defun c:lcnt  () (cn7_ltype "CENTER2") (princ))
(defun c:lpht  () (cn7_ltype "PHANTOM2") (princ))
(defun c:ldot  () (cn7_ltype "DOT2") (princ))
(defun c:ldsd  () (cn7_ltype "DASHDOT2") (princ))
(defun c:ldvd  () (cn7_ltype "DIVIDE2") (princ))
(defun c:lst1  () (cn7_ltype "SETA1") (princ))
(defun c:lst2  () (cn7_ltype "SETA2") (princ))
(defun c:lst3  () (cn7_ltype "SETA3") (princ))
(defun c:lccl  () (cn7_ltype "CIRCULO"))

;grupo II - linhas especiais
(defun c:lcrc  () (cn7_ltype "CERCA")(princ))
(defun c:linc  () (cn7_ltype "INCENDIO")(princ))
(defun c:lprr  () (cn7_ltype "PRAIO"))
(defun c:lins  () (cn7_ltype "INSTRUMENT")(princ))
(defun c:ltrl  () (cn7_ltype "TRILHO")(princ))
(defun c:lalt  () (cn7_ltype "ATENSAO")(princ))
(defun c:lter  () (cn7_ltype "TERRA")(princ))
(defun c:lrc1  () (cn7_ltype "ROCHA1")(princ))
(defun c:lrc2  () (cn7_ltype "ROCHA2")(princ))
(defun c:lcpc  () (cn7_ltype "CAPACITOR")(princ))
(defun c:lprg  () (cn7_ltype "PERIGO")(princ))
(defun c:lcel  () (cn7_ltype "CERCAELETR")(princ))


;******************************************************************
;Linhas Criadas
;******************************************************************
(defun cn7_ltype (lin)
  (cond
    ;grupo I
    ((= lin "INTERRUP") (setq cn7_ltype_lay "Ltype_interrupção"))
    ((= lin "HIDDEN") (setq cn7_ltype_lay "Ltype_hidden"))
    ((= lin "HIDDEN2") (setq cn7_ltype_lay "Ltype_hidden2"))
    ((= lin "CENTER2") (setq cn7_ltype_lay "Ltype_center"))
    ((= lin "PHANTOM2") (setq cn7_ltype_lay "Ltype_phantom"))
    ((= lin "DOT2") (setq cn7_ltype_lay "Ltype_dot"))
    ((= lin "DASHDOT2") (setq cn7_ltype_lay "Ltype_dashdot"))
    ((= lin "DIVIDE2") (setq cn7_ltype_lay "Ltype_divide"))
    ((= lin "SETA1") (setq cn7_ltype_lay "Ltype_seta1"))
    ((= lin "SETA2") (setq cn7_ltype_lay "Ltype_seta2"))
    ((= lin "SETA3") (setq cn7_ltype_lay "Ltype_seta3"))
    ((= lin "CIRCULO") (setq cn7_ltype_lay "Ltype_circulo"))
    ;grupo II
    ((= lin "CERCA") (setq cn7_ltype_lay "Ltype_cerca"))
    ((= lin "INCENDIO") (setq cn7_ltype_lay "Ltype_incêndio"))
    ((= lin "PRAIO") (setq cn7_ltype_lay "Ltype_para-raio"))
    ((= lin "TRILHO") (setq cn7_ltype_lay "Ltype_trilho"))
    ((= lin "ATENSAO") (setq cn7_ltype_lay "Ltype_alta-tensão"))
    ((= lin "ROCHA1") (setq cn7_ltype_lay "Ltype_rocha_1"))
    ((= lin "ROCHA2") (setq cn7_ltype_lay "Ltype_rocha_2"))
    ((= lin "TERRA") (setq cn7_ltype_lay "Ltype_terra"))
    ((= lin "INSTRUMENT") (setq cn7_ltype_lay "Ltype_instrumentação"))
    ((= lin "CAPACITOR") (setq cn7_ltype_lay "Ltype_capacitor"))
    ((= lin "PERIGO") (setq cn7_ltype_lay "Ltype_perigo"))
    ((= lin "CERCAELETR") (setq cn7_ltype_lay "Ltype_cerca_elétrica"))
  )
  (if (not (tblsearch "ltype" lin))
    (command "._linetype" "_l" lin (strcat cnp_root "/modelos/cadnorma.lin") "")
    (command "._linetype" "_l" lin (strcat cnp_root "/modelos/cadnorma.lin") "_y" "")
  );if
  (if (/= nil (setq ltype_laylist (tblsearch "layer" cn7_ltype_lay)))
    (progn
      (setq ltype_laycol (cdr (assoc 62 ltype_laylist)))
      (cn7_verylayer cn7_ltype_lay ltype_laycol)
    )
    (command "._layer" "_m" cn7_ltype_lay "_lt" lin "" "_c" (acad_colordlg 7) "" "")
  )
  (setq pt (getpoint "\nPonto Inicial... "))
  (command "._line" pt)
);defun
	  

;Mudar para layers com linhas especiais
(defun toltype (lin)
  (guarda '("blipmode" "cecolor" "celtype" "clayer" "cmdecho" "orthomode"
	    "textstyle" "luprec" "osmode" ))
  (cond
    ;grupo I
    ((= lin "INTERRUP") (setq cn7_ltype_lay "Ltype_interrupção"))
    ((= lin "HIDDEN") (setq cn7_ltype_lay "Ltype_hidden"))
    ((= lin "HIDDEN2") (setq cn7_ltype_lay "Ltype_hidden2"))
    ((= lin "CENTER2") (setq cn7_ltype_lay "Ltype_center"))
    ((= lin "PHANTOM2") (setq cn7_ltype_lay "Ltype_phantom"))
    ((= lin "DOT2") (setq cn7_ltype_lay "Ltype_dot"))
    ((= lin "DASHDOT2") (setq cn7_ltype_lay "Ltype_dashdot"))
    ((= lin "DIVIDE2") (setq cn7_ltype_lay "Ltype_divide"))
    ((= lin "SETA1") (setq cn7_ltype_lay "Ltype_seta1"))
    ((= lin "SETA2") (setq cn7_ltype_lay "Ltype_seta2"))
    ((= lin "SETA3") (setq cn7_ltype_lay "Ltype_seta3"))
    ((= lin "CIRCULO") (setq cn7_ltype_lay "Ltype_circulo"))
    ;grupo II
    ((= lin "CERCA") (setq cn7_ltype_lay "Ltype_cerca"))
    ((= lin "INCENDIO") (setq cn7_ltype_lay "Ltype_incêndio"))
    ((= lin "PRAIO") (setq cn7_ltype_lay "Ltype_para-raio"))
    ((= lin "TRILHO") (setq cn7_ltype_lay "Ltype_trilho"))
    ((= lin "ATENSAO") (setq cn7_ltype_lay "Ltype_alta-tensão"))
    ((= lin "ROCHA1") (setq cn7_ltype_lay "Ltype_rocha_1"))
    ((= lin "ROCHA2") (setq cn7_ltype_lay "Ltype_rocha_2"))
    ((= lin "TERRA") (setq cn7_ltype_lay "Ltype_terra"))
    ((= lin "INSTRUMENT") (setq cn7_ltype_lay "Ltype_instrumentação"))
    ((= lin "CAPACITOR") (setq cn7_ltype_lay "Ltype_capacitor"))
    ((= lin "PERIGO") (setq cn7_ltype_lay "Ltype_perigo"))
    ((= lin "CERCAELETR") (setq cn7_ltype_lay "Ltype_cerca_elétrica"))
  )
  (if (not (tblsearch "ltype" lin))
    (command "._linetype" "_l" lin (strcat cnp_root "/modelos/cadnorma.lin") "")
    (command "._linetype" "_l" lin (strcat cnp_root "/modelos/cadnorma.lin") "_y" "")
  )
  (if (not (tblsearch "layer" cn7_ltype_lay))
    (command "._layer" "_m" cn7_ltype_lay "_lt" lin "" "_c" (acad_colordlg 7) "" "")
  )
  (prompt (strcat "\nSelecione os objetos para linha <" lin ">..."))
  (setq s1 (ssget))
  (command "._chprop" "_p" "" "_la" cn7_ltype_lay "_lt" "bylayer" "")
  (devolve)
  (princ)
)

;cnp_07


;******************************************************************************
;******************************************************************************
;Textos
;******************************************************************************
;******************************************************************************
;COMANDOS DE CRIAÇÃO DE TEXTOS NOS ESTILOS

;fonte romans
(defun c:r50 () (cn7_wrtext1 "r50"))
(defun c:r60 () (cn7_wrtext1 "r60"))
(defun c:r70 () (cn7_wrtext1 "r70"))
(defun c:r80 () (cn7_wrtext1 "r80"))
(defun c:r90 () (cn7_wrtext1 "r90"))
(defun c:r100 () (cn7_wrtext1 "r100"))
(defun c:r120 () (cn7_wrtext1 "r120"))
(defun c:r140 () (cn7_wrtext1 "r140"))
(defun c:r175 () (cn7_wrtext1 "r175"))
(defun c:r200 () (cn7_wrtext1 "r200"))

  
;escrita de texto - Carburador
(defun cn7_wrtext1 (n)
  (guarda '("blipmode" "cecolor" "celtype" "clayer" "cmdecho" "orthomode"
          "textstyle" "luprec" "osmode" ))
  (setq cn7_txtsty n)
  (cn7_text_hfinal)
  (cn7_text_height)
  (cn7_wrtext)
  (devolve)
)

(defun cn7_wrtext ()
  (if (not (tblsearch "style" cn7_txtsty))
    (progn
      (cn7_alert_ok
	"O estilo solicitado não existe!"
	"Digite <CFG> para configurar o desenho!"
	"")
      (exit)
    )
    (cn7_do_writext)
  )
)

;escreve efetivamente o texto
(defun cn7_do_writext ()
  (cond
    ((= cn7_txtsty "r50") (setq cn7_txlay (strcat cn7_prefixlay "txt_r50") cn7_txcol 1))
    ((= cn7_txtsty "r60") (setq cn7_txlay (strcat cn7_prefixlay "txt_r60") cn7_txcol 1))
    ((= cn7_txtsty "r70") (setq cn7_txlay (strcat cn7_prefixlay "txt_r70") cn7_txcol 2))
    ((= cn7_txtsty "r80") (setq cn7_txlay (strcat cn7_prefixlay "txt_r80") cn7_txcol 2))
    ((= cn7_txtsty "r90") (setq cn7_txlay (strcat cn7_prefixlay "txt_r90") cn7_txcol 3))
    ((= cn7_txtsty "r100") (setq cn7_txlay (strcat cn7_prefixlay "txt_r100") cn7_txcol 3))
    ((= cn7_txtsty "r120") (setq cn7_txlay (strcat cn7_prefixlay "txt_r120") cn7_txcol 4))
    ((= cn7_txtsty "r140") (setq cn7_txlay (strcat cn7_prefixlay "txt_r140") cn7_txcol 5))
    ((= cn7_txtsty "r175") (setq cn7_txlay (strcat cn7_prefixlay "txt_r175") cn7_txcol 6))
    ((= cn7_txtsty "r200") (setq cn7_txlay (strcat cn7_prefixlay "txt_r200") cn7_txcol 6))
  )
  (prompt "\nMarque o ponto inicial do texto...")
  (if (= cdn_txt 1)
    (cn7_verylayer cn7_txlay cn7_txcol)
  )	
  (txt_final_write)
)
    
(defun txt_final_write ()
  (initget 128)
  (setq resp (getpoint "\nCenter/Middle/Right/<Marque o Ponto>: "))
  (cond
    ((= 'LIST (type resp))
     (command "._dtext" "_s" cn7_txtsty "_non" resp cn7_txth))
    ((= 'STR  (type resp))
     (cond
       ((= "C" (strcase resp))
	(setq ptx (getpoint "\nMarque o ponto Central do texto..."))
	(command "._dtext" "_s" cn7_txtsty "c" "_non" ptx cn7_txth))
       ((= "M" (strcase resp))
	(setq ptx (getpoint "\nMarque o ponto Middle do texto..."))
	(command "._dtext" "_s" cn7_txtsty "m" "_non" ptx cn7_txth))
       ((= "R" (strcase resp))
	(setq ptx (getpoint "\nMarque o ponto Central do texto..."))
	(command "._dtext" "_s" cn7_txtsty "r" "_non" ptx cn7_txth))
       (t
	(prompt "Opção inválida! Escolha um ponto ou um alinhamento válido...")
	(exit))
     );cond
   )
  )
  (princ)
)


;Texto Pessoal
(defun c:t1 () (cn7_wrtext2 "t1"))
(defun c:t2 () (cn7_wrtext2 "t2"))
(defun c:t3 () (cn7_wrtext2 "t3"))
(defun c:t4 () (cn7_wrtext2 "t4"))
(defun c:t5 () (cn7_wrtext2 "t5"))
(defun c:t6 () (cn7_wrtext2 "t6"))
(defun c:t7 () (cn7_wrtext2 "t7"))

;carburdor
(defun cn7_wrtext2 (n)
  (cn7_cfg_altext_file)
  (setq cn7_txtsty n)
  (cond
    ((= n "t1") (setq cn7_txthf (distof t1_alt)))
    ((= n "t2") (setq cn7_txthf (distof t2_alt)))
    ((= n "t3") (setq cn7_txthf (distof t3_alt)))
    ((= n "t4") (setq cn7_txthf (distof t4_alt)))
    ((= n "t5") (setq cn7_txthf (distof t5_alt)))
    ((= n "t6") (setq cn7_txthf (distof t6_alt)))
    ((= n "t7") (setq cn7_txthf (distof t7_alt)))
  )
  (cn7_text_height)
  (if (not (tblsearch "style" cn7_txtsty))
    (progn
      (cn7_alert_ok
	(strcat "O estilo de texto '" n "' não existe!")
	"Digite <CFG> e habilite a opção"
	"'Texto Pessoal' para criá-lo!")
      (exit)
    )
    (cn7_do_writext2)
  )
)

(defun cn7_do_writext2 ()
  (cond
    ((= cn7_txtsty "t1") (setq cn7_txlay (strcat cn7_prefixlay "txt_t1") cn7_txcol (fix (distof t1_col))))
    ((= cn7_txtsty "t2") (setq cn7_txlay (strcat cn7_prefixlay "txt_t2") cn7_txcol (fix (distof t2_col))))
    ((= cn7_txtsty "t3") (setq cn7_txlay (strcat cn7_prefixlay "txt_t3") cn7_txcol (fix (distof t3_col))))
    ((= cn7_txtsty "t4") (setq cn7_txlay (strcat cn7_prefixlay "txt_t4") cn7_txcol (fix (distof t4_col))))
    ((= cn7_txtsty "t5") (setq cn7_txlay (strcat cn7_prefixlay "txt_t5") cn7_txcol (fix (distof t5_col))))
    ((= cn7_txtsty "t6") (setq cn7_txlay (strcat cn7_prefixlay "txt_t6") cn7_txcol (fix (distof t6_col))))
    ((= cn7_txtsty "t7") (setq cn7_txlay (strcat cn7_prefixlay "txt_t7") cn7_txcol (fix (distof t7_col))))
  )
  (prompt "\nMarque o ponto inicial do texto...")
  (if (= cus_txt 1)
    (cn7_verylayer cn7_txlay cn7_txcol)
  )
  (txt_final_write)
)

;*************************************************************************
;*************************************************************************
;COMANDO DE ALTERAÇÃO DE TEXTOS
;*************************************************************************
;*************************************************************************
(defun ptext (n)
  (guarda '("blipmode" "cecolor" "celtype" "clayer" "cmdecho" "orthomode"
          "textstyle" "luprec" "osmode" ))
  (cond
    ((= n "r50") (setq cn7_txtsty "r50" cn7_ptext_col 1 ))
    ((= n "r60") (setq cn7_txtsty "r60" cn7_ptext_col 1))
    ((= n "r70") (setq cn7_txtsty "r70" cn7_ptext_col 2))
    ((= n "r80") (setq cn7_txtsty "r80" cn7_ptext_col 2))
    ((= n "r90") (setq cn7_txtsty "r90" cn7_ptext_col 3))
    ((= n "r100") (setq cn7_txtsty "r100" cn7_ptext_col 3))
    ((= n "r120") (setq cn7_txtsty "r120" cn7_ptext_col 4))
    ((= n "r140") (setq cn7_txtsty "r140" cn7_ptext_col 5))
    ((= n "r175") (setq cn7_txtsty "r175" cn7_ptext_col 6))
    ((= n "r200") (setq cn7_txtsty "r200" cn7_ptext_col 6))
  )
  (setq cn7_ptext_sty n)
  (cn7_text_hfinal)
  (cn7_text_height)
  (cond
    ((= n "r50") (setq cn7_ptext_lay (strcat cn7_prefixlay "txt_r50")))
    ((= n "r60") (setq cn7_ptext_lay (strcat cn7_prefixlay "txt_r60")))
    ((= n "r70") (setq cn7_ptext_lay (strcat cn7_prefixlay "txt_r70")))
    ((= n "r80") (setq cn7_ptext_lay (strcat cn7_prefixlay "txt_r80")))
    ((= n "r90") (setq cn7_ptext_lay (strcat cn7_prefixlay "txt_r90")))
    ((= n "r100") (setq cn7_ptext_lay (strcat cn7_prefixlay "txt_r100")))
    ((= n "r120") (setq cn7_ptext_lay (strcat cn7_prefixlay "txt_r120")))
    ((= n "r140") (setq cn7_ptext_lay (strcat cn7_prefixlay "txt_r140")))
    ((= n "r175") (setq cn7_ptext_lay (strcat cn7_prefixlay "txt_r175")))
    ((= n "r200") (setq cn7_ptext_lay (strcat cn7_prefixlay "txt_r200")))
  )
  (cn7_prtext)
  (devolve)
  (princ)
)

(defun cn7_prtext ()
  (setq counter 0)
  (prompt "\nSelecione o trecho para alteração dos textos...")
  (setq   s1 (ssget '((0 . "TEXT"))))
  (setq
    n_element (sslength s1)
    counter 0
  )
  (cn7_verylayer cn7_ptext_lay cn7_ptext_col)
  (repeat n_element
    (setq s1_ent (ssname s1 counter))
    (setq ent_list (entget s1_ent))
    ;corrige a altura
    (setq ent_list (entmod (subst (cons 40  cn7_txth) (assoc 40 ent_list) ent_list)))
    (setq ent_list (entmod (subst (cons 7  cn7_txtsty) (assoc 7 ent_list) ent_list)))
    (if (= cdn_txt 1)
      (cond
	((= cn7_ptext_sty "r50") (setq ent_list (entmod (subst (cons 8  (strcat cn7_prefixlay "txt_r50")) (assoc 8 ent_list) ent_list))))
	((= cn7_ptext_sty "r60") (setq ent_list (entmod (subst (cons 8  (strcat cn7_prefixlay "txt_r60")) (assoc 8 ent_list) ent_list))))
	((= cn7_ptext_sty "r70") (setq ent_list (entmod (subst (cons 8  (strcat cn7_prefixlay "txt_r70")) (assoc 8 ent_list) ent_list))))
	((= cn7_ptext_sty "r80") (setq ent_list (entmod (subst (cons 8  (strcat cn7_prefixlay "txt_r80")) (assoc 8 ent_list) ent_list))))
	((= cn7_ptext_sty "r90") (setq ent_list (entmod (subst (cons 8  (strcat cn7_prefixlay "txt_r90")) (assoc 8 ent_list) ent_list))))
	((= cn7_ptext_sty "r100") (setq ent_list (entmod (subst (cons 8  (strcat cn7_prefixlay "txt_r100")) (assoc 8 ent_list) ent_list))))
	((= cn7_ptext_sty "r120") (setq ent_list (entmod (subst (cons 8  (strcat cn7_prefixlay "txt_r120")) (assoc 8 ent_list) ent_list))))
	((= cn7_ptext_sty "r140") (setq ent_list (entmod (subst (cons 8  (strcat cn7_prefixlay "txt_r140")) (assoc 8 ent_list) ent_list))))
	((= cn7_ptext_sty "r175") (setq ent_list (entmod (subst (cons 8  (strcat cn7_prefixlay "txt_r175")) (assoc 8 ent_list) ent_list))))
	((= cn7_ptext_sty "r200") (setq ent_list (entmod (subst (cons 8  (strcat cn7_prefixlay "txt_r200")) (assoc 8 ent_list) ent_list))))
      )
    )
    (setq counter (1+ counter))
  )
)



;alteração de textos custom
(defun ptext2 (n)
  (guarda '("blipmode" "cecolor" "celtype" "clayer" "cmdecho" "orthomode"
          "textstyle" "luprec" "osmode" ))
  (cn7_cfg_altext_file)
  (cond
    ((= n "t1") (setq cn7_txtsty "t1" cn7_ptext_col (fix (distof t1_col))))
    ((= n "t2") (setq cn7_txtsty "t2" cn7_ptext_col (fix (distof t2_col))))
    ((= n "t3") (setq cn7_txtsty "t3" cn7_ptext_col (fix (distof t3_col))))
    ((= n "t4") (setq cn7_txtsty "t4" cn7_ptext_col (fix (distof t4_col))))
    ((= n "t5") (setq cn7_txtsty "t5" cn7_ptext_col (fix (distof t5_col))))
    ((= n "t6") (setq cn7_txtsty "t6" cn7_ptext_col (fix (distof t6_col))))
    ((= n "t7") (setq cn7_txtsty "t7" cn7_ptext_col (fix (distof t7_col))))
  )
  (setq cn7_ptext_sty n)
  (cn7_text_hfinal)
  (cn7_text_height)
  (cond
    ((= n "t1") (setq cn7_ptext_lay (strcat cn7_prefixlay "txt_t1")))
    ((= n "t2") (setq cn7_ptext_lay (strcat cn7_prefixlay "txt_t2")))
    ((= n "t3") (setq cn7_ptext_lay (strcat cn7_prefixlay "txt_t3")))
    ((= n "t4") (setq cn7_ptext_lay (strcat cn7_prefixlay "txt_t4")))
    ((= n "t5") (setq cn7_ptext_lay (strcat cn7_prefixlay "txt_t5")))
    ((= n "t6") (setq cn7_ptext_lay (strcat cn7_prefixlay "txt_t6")))
    ((= n "t6") (setq cn7_ptext_lay (strcat cn7_prefixlay "txt_t7")))
  )
  (cn7_prtext2)
  (devolve)
  (princ)
)

(defun cn7_prtext2 ()
  (setq counter 0)
  (prompt "\nSelecione o trecho para alteração dos textos...")
  (setq   s1 (ssget '((0 . "TEXT"))))
  (setq
    n_element (sslength s1)
    counter 0
  )
  (cn7_verylayer cn7_ptext_lay cn7_ptext_col)
  (repeat n_element
    (setq s1_ent (ssname s1 counter))
    (setq ent_list (entget s1_ent))
    ;corrige a altura
    (setq ent_list (entmod (subst (cons 40  cn7_txth) (assoc 40 ent_list) ent_list)))
    (setq ent_list (entmod (subst (cons 7  cn7_txtsty) (assoc 7 ent_list) ent_list)))
    (if (= cus_txt 1)
      (cond
	((= cn7_ptext_sty "t1") (setq ent_list (entmod (subst (cons 8  (strcat cn7_prefixlay "txt_t1")) (assoc 8 ent_list) ent_list))))
	((= cn7_ptext_sty "t2") (setq ent_list (entmod (subst (cons 8  (strcat cn7_prefixlay "txt_t2")) (assoc 8 ent_list) ent_list))))
	((= cn7_ptext_sty "t3") (setq ent_list (entmod (subst (cons 8  (strcat cn7_prefixlay "txt_t3")) (assoc 8 ent_list) ent_list))))
	((= cn7_ptext_sty "t4") (setq ent_list (entmod (subst (cons 8  (strcat cn7_prefixlay "txt_t4")) (assoc 8 ent_list) ent_list))))
	((= cn7_ptext_sty "t5") (setq ent_list (entmod (subst (cons 8  (strcat cn7_prefixlay "txt_t5")) (assoc 8 ent_list) ent_list))))
	((= cn7_ptext_sty "t6") (setq ent_list (entmod (subst (cons 8  (strcat cn7_prefixlay "txt_t6")) (assoc 8 ent_list) ent_list))))
	((= cn7_ptext_sty "t7") (setq ent_list (entmod (subst (cons 8  (strcat cn7_prefixlay "txt_t7")) (assoc 8 ent_list) ent_list))))
      )
    )
    (setq counter (1+ counter))
  )
)

;cnp_08


;******************************************************************************
;******************************************************************************
;Textos - Ferramentas
;******************************************************************************
;******************************************************************************

;Alinhar Textos
(defun c:txa ()
  (setq counter 0)
  (prompt "\nSelecione os Textos a alinhar...")
  (setq s1 (ssget '((0 . "TEXT"))))
  (if (= nil s1) (exit))
  (initget "Vertical Horizontal")
  (setq resp (getkword "\nHorizontal/<Vertical>..."))
  (if (= nil resp) (setq resp "Vertical"))
  (initget "Left Center Right")
  (setq resp2 (getkword "\nTipo de alinhamento...Right/Center/<Left>..."))
  (if (= nil resp2) (setq resp2 "Left"))
  (setq txa_pto (getpoint "\nPonto de alinhamento...")
	txa_xpto (nth 0 txa_pto)
	txa_ypto (nth 1 txa_pto)
  )  
  (setq	s1_len (sslength s1))
  (cond
    ((= resp2 "Left") (setq txa_ali 0))
    ((= resp2 "Center") (setq txa_ali 1))
    ((= resp2 "Right") (setq txa_ali 2))
  )
  (repeat s1_len
    (setq txt_list (entget (ssname s1 counter))
	  txt_xpto (nth 1 (assoc 10 txt_list))
	  txt_ypto (nth 2 (assoc 10 txt_list))
	  txt_zpto (nth 3 (assoc 10 txt_list))
	  txt_list (entmod (subst (cons 72 txa_ali) (assoc 72 txt_list) txt_list))
    )
    (if (= resp "Vertical")
        (command "._change" (ssname s1 counter) "" "" "_non" (list txa_xpto txt_ypto txt_zpto) "" "" "" "")
        (command "._change" (ssname s1 counter) "" "" "_non" (list txt_xpto txa_ypto txt_zpto) "" "" "" "")
    )
    
    (setq counter (1+ counter))
  )
  (princ)
)
;Funcao RTX - Roda Textos
(defun c:rtx ()
  (setq laymo (getvar "clayer"))
  (setq osmo (getvar "osmode"))
  (setvar "osmode" 0)
  (prompt "\nSelecione os textos a serem rodados...")
  (setq s1 (ssget '((0 . "TEXT"))))
  (setq rot (getreal "\nAngulo de rotação (em graus): "))
  (setq count_limit (sslength s1) counter 0)
  (command "._undo" "_m")
  (repeat count_limit
    (setq ent1 (ssname s1 counter))
    (setq ent2 ent1)
    (setq p0 (cdr (assoc 10 (entget ent1))))
    (command "._rotate" ent1 "" p0 rot)
    (setq counter (1+ counter))
  );repeat
  (setvar "clayer" laymo)
  (setvar "osmode" osmo)
  (prompt "\nUse o comando <UB> para retornar... ")
  (princ)
)

;direção de textos
(defun c:dtx ()
  (prompt "\nSelecione os textos a serem rotacionados...")
  (setq s1 (ssget '((0 . "TEXT"))))
  (initget 128)
  (setq pt1 (getpoint "\nAngulo de rotação / <Primeiro ponto>..."))
  (cond
    ;se clicar num ponto
    ((= 'LIST (type pt1))
     (setq pt2 (getpoint pt1 "\nSegundo ponto para alinhamento...")
	   angrad (angle pt1 pt2)
     )
    )
    ((= 'STR  (type pt1))
     (cond
       ((= "A" (strcase pt1))
	(setq angdeg (getreal "\nEntre com o ângulo de rotação em graus...")
	      angrad (/ (* angdeg pi) 180))
       )
       (t
	(prompt "\nOpção inválida... Marque o primeiro ponto ou digite <A> para entrar com o ângulo...")
	(quit)
       )
     )
    )
  )
  (setq count_limit (sslength s1) counter 0)
  (repeat count_limit
    (setq ent1 (ssname s1 counter)
	  ent1_list (entget ent1)
	  ent1_list (entmod (subst (cons 50 angrad) (assoc 50 ent1_list) ent1_list))
	  counter (1+ counter)
    )
  );repeat
  (princ)
)

;igualar rotação de textos
(defun c:trot ()
  (prompt "\nSelecione o texto de referência...")
  (setq ent1 (entsel)
	ent1_list (entget (car ent1))
	ent1_type (cdr (assoc 0 ent1_list))
  )
  (if (/= ent1_type "TEXT")
    (progn
      (prompt "\nA entidade selecionada não é um texto!")
      (quit)
    )
    (progn
      (setq tx_rot (cdr (assoc 50 ent1_list)))
      (prompt "\nSelecione os textos para igualar a rotação...")
      (setq s1 (ssget '((0 . "TEXT")))
	    s1_len (sslength s1)
	    counter 0
      )
      (repeat s1_len
	(setq ent2 (ssname s1 counter)
	      ent2_list (entget ent2)
	      ent2_list (entmod (subst (cons 50 tx_rot) (assoc 50 ent2_list) ent2_list))
	      counter (1+ counter)
	)
      )
    )
  )
  (princ)
)


;caixa em volta do texto
(defun c:tbox ()
  (guarda '("blipmode" "cecolor" "celtype" "clayer" "cmdecho" "orthomode"
        "textstyle" "luprec" "osmode" ))
  (setq textent (car (entsel "\nSelecione o texto : ")))
  (if textent
    (setq textent_lay (cdr (assoc 8 (entget textent))))
  )
  (setvar "osmode" 0)
  (setq grp_type "2")
  (cn7_find_blkscl)
  (command "._ucs" "_entity" textent)
  (setq tb (textbox (list (cons -1 textent)))
        ll (car tb)
        ur (cadr tb)
        ul (list (car ll) (cadr ur))
        lr (list (car ur) (cadr ll))
        os (polar ll (angle lr ll) (* 0.075 cn7_blkscl))
  )
  (command "._layer" "_s" textent_lay "" "._pline" ll lr ur ul "_close")
  (setq tbox_last (entlast))
  (command "._offset" "_t" tbox_last os "")
  (command "._erase" tbox_last "")
  (command "._ucs" "_p" )
  (initget "Sim Não")
  (setq resp (getkword "\nDeseja uma hachura sólida com a cor 9 no texto (S / <N>)? "))
  (if (= resp nil) (setq resp "Não"))
  (if (= resp "Sim")
    (command "._hatch" "_Solid" (entlast) "" "._chprop" (entlast) "" "_p" "_c" "9" "" "._draworder" (entlast) "" "_b")
  )
  (devolve)
  (princ)
)

;caixa em volta do parágrafo
(defun c:pbox ()
  (guarda '("blipmode" "cecolor" "celtype" "clayer" "cmdecho" "orthomode"
          "textstyle" "luprec" "osmode" ))
  (setq grp_type "2")
  (cn7_find_blkscl)
  (setq s1 (ssget '((0 . "TEXT")))
	s1_len (sslength s1)
	counter 0
	xmin nil ymin nil xmax nil ymax nil)
  (repeat s1_len
    (setq ent (ssname s1 counter))
    (command "._ucs" "_entity" ent)
    (setq
	  ent_list (entget ent)
	  tb (textbox ent_list)
	  ll (trans (car tb) 1 0);lower left
	  x_ll (nth 0 ll)
	  y_ll (nth 1 ll)
	  ur (trans (cadr tb) 1 0);upper rigth
	  x_ur (nth 0 ur)
	  y_ur (nth 1 ur)
	  text_lay (cdr (assoc 8 ent_list))
    )
    (if (or (= xmin nil) (<= x_ll xmin)) (setq xmin x_ll))
    (if (or (= ymin nil) (<= y_ll ymin)) (setq ymin y_ll))
    (if (or (= xmax nil) (>= x_ur xmax)) (setq xmax x_ur))
    (if (or (= ymax nil) (>= y_ur ymax)) (setq ymax y_ur))
    (setq counter (1+ counter))
  )
  (setq p_ll (list xmin ymin 0.0)
	p_ur (list xmax ymax 0.0)
	p_lr (list xmax ymin 0.0)
	p_ul (list xmin ymax 0.0)
	os (polar p_ll pi (* 0.1 cn7_blkscl))
  )
  (command "._ucs" "_w" "._layer" "_s" text_lay "" "._pline" "_non" p_ll "_non" p_lr "_non" p_ur "_non" p_ul "_c")
  (setq tbox_last (entlast))
  (command "._offset" "_t" tbox_last "_non" os "")
  (command "._erase" tbox_last "")
  (initget "Sim Não")
  (setq resp (getkword "\nDeseja uma hachura sólida com a cor 9 no parágrafo? (S / <N>)? "))
  (if (= resp nil) (setq resp "Não"))
  (if (= resp "Sim")
    (command "._hatch" "_Solid" (entlast) "" "._chprop" (entlast) "" "_p" "_c" "9" "" "._draworder" (entlast) "" "_b")
  )
  (devolve)
  (princ)
)

;círculo em volta do texto
(defun c:cbox ()
  (guarda '("blipmode" "cecolor" "celtype" "clayer" "cmdecho" "orthomode"
          "textstyle" "luprec" "osmode" ))
  (setq textent_list (entget (car (entsel "\nSelecione o texto : "))))
  (if textent_list
    (setq textent_lay (cdr (assoc 8 textent_list)))
  )
  (setvar "osmode" 0)
  (setq grp_type "2")
  (cn7_find_blkscl)
  (command "._ucs" "_entity" (cdr (assoc -1 textent_list)))
  (setq tb (textbox textent_list)
	p1 (car tb)
	p2 (cadr tb)
	pc (polar p1 (angle p1 p2) (/ (distance p1 p2) 2))
  )
  (command "._layer" "_s" textent_lay "" "._circle" "_non" pc "_non" p2 "._scale" (entlast) "" "_non" pc 1.1)
  (command "._ucs" "_w" )
  (initget "Sim Não")
  (setq resp (getkword "\nDeseja uma hachura sólida com a cor 9 no círculo (S / <N>)? "))
  (if (= resp nil) (setq resp "Não"))
  (if (= resp "Sim")
    (command "._hatch" "_Solid" (entlast) "" "._chprop" (entlast) "" "_p" "_c" "9" "" "._draworder" (entlast) "" "_b")
  )
  (devolve)
  (princ)
)

;Coloca um Point no Insert de cada Texto
(defun c:ptx ()
  (guarda '("blipmode" "cecolor" "celtype" "clayer" "cmdecho" "orthomode"
          "textstyle" "luprec" "osmode" ))
	(setvar "osmode" 0)
  	(command "._layer" "_m" "txt_point" "_c" "4" "" "")
	(prompt "\nSelecione os textos a receberem pontos <node>...")
	(setq s1 (ssget))
	(setq count_limit (sslength s1) counter 0)
	(repeat count_limit
		(setq ent1 (ssname s1 counter))
		(setq ent2 ent1)
		(if (=  (strcase (cdr (assoc 0 (entget ent1)))) "TEXT")
			(progn
			  	(setq p0 (cdr (assoc 10 (entget ent1))))
			  	(command "._point" p0)
			)
		);if
		(setq counter (1+ counter))
	);repeat
  (devolve)  
  (princ)
);defun


;Soma Textos
(defun c:soma ()
  (cn7_init)
  (guarda '("blipmode" "cecolor" "celtype" "clayer" "cmdecho" "orthomode"
          "textstyle" "luprec" "osmode" ))
  (setq cn7_dzin (getvar "dimzin"))
  (prompt "\nSelecione os textos a serem somados...")
  (setq s1 (ssget '((0 . "TEXT"))))
  (if (not txt_dec)
    (progn
      (setq txt_dec (getint "\nNúmero de casas decimais do resultado...< 0 >..."))
      (if (= nil txt_dec) (setq txt_dec 0))
    )
    (progn
      (setq txt_dec_new (getint (strcat "\nNúmero de casas decimais do resultado...< " (rtos txt_dec 2 0) " >...")))
      (if (/= txt_dec_new nil) (setq txt_dec txt_dec_new))
    )
  )
  (setvar "dimzin" 1)
  (setq s1_len (sslength s1) counter 0 txt_soma 0.00)
  (repeat s1_len
    (setq curr_ent (ssname s1 counter))
    (if (distof (cdr (assoc 1 (entget curr_ent))))
      (progn
	(setq txt_soma (+ txt_soma (distof (cdr (assoc 1 (entget curr_ent))))))
	(setq counter (1+ counter))
      )
      (setq counter (1+ counter))
    )
  );repeat
  (prompt (strcat "Soma = " (rtos txt_soma 2 2)))
  (initget 1 "Escrever Modificar")
  (setq resp (getkword "\nEscrever ou Modificar texto existente ? <E ou M> "))
  (if (= resp "Escrever")
    (progn
      (cn7_getstyle)
      (cn7_text_hfinal)
      (cn7_text_height)
      (setq psimb_txt (getpoint "\nPonto de Inserção..."))
      (cn7_txsimb cn7_txtsty "_bl" (rtos txt_soma 2 txt_dec) getsty_col getsty_lay 0)
    );progn
    (progn
      (princ "Selecione o texto a receber o resultado...")
      (setq ent2 (entsel))
      (setq new (cons 1 (rtos txt_soma 2 txt_dec)))
      (entmod (subst new (assoc 1 (entget (car ent2))) (entget (car ent2))))
    );progn
  );if
  (devolve)
  (princ)
)

;subtrai textos
(defun c:subt ()
  (cn7_init)
  (guarda '("blipmode" "cecolor" "celtype" "clayer" "cmdecho" "orthomode"
          "textstyle" "luprec" "osmode" ))
  (setq cn7_dzin (getvar "dimzin"))
  (setq minuendo (entsel "\nSelecione o primeiro texto (Minuendo)..."))
  (if (= nil minuendo) (exit))
  (if (/= "TEXT" (cdr (assoc 0 (entget (car minuendo)))))
    (progn
      (alert "\nObjeto selecionado não é um texto...")
      (exit)
    )
    (progn
      (if (not (distof (cdr (assoc 1 (entget (car minuendo))))))
	(progn
	  (alert "\nO texto selecionado não corresponde a um número...")
	  (exit)
	)
      )
    )
  )
  (setq txt_minuendo (distof (cdr (assoc 1 (entget (car minuendo))))))
  (prompt "\nSelecione os textos a serem subtraídos do primeiro (Subtraendo)...")
  (setq s1 (ssget '((0 . "TEXT"))))
  (setq txt_dec (getint "\nNúmero de casas decimais do resultado...<Enter = 0>..."))
  (if (= nil txt_dec) (setq txt_dec 0))
  (setvar "dimzin" 1)
  (setq s1_len (sslength s1) counter 0 txt_soma 0.00)
  (repeat s1_len
    (setq curr_ent (ssname s1 counter))
    (if (distof (cdr (assoc 1 (entget curr_ent))))
      (progn
	(setq txt_soma (+ txt_soma (distof (cdr (assoc 1 (entget curr_ent))))))
	(setq counter (1+ counter))
      )
      (setq counter (1+ counter))
    )
  );repeat
  (setq txt_resto (- txt_minuendo txt_soma))
  (prompt (strcat "Resto = " (rtos txt_resto 2 2)))
  (initget 1 "Escrever Modificar")
  (setq resp (getkword "\nEscrever ou Modificar texto existente ? <E ou M> "))
  (if (= resp "Escrever")
    (progn
      (cn7_getstyle)
      (cn7_text_hfinal)
      (cn7_text_height)
      (setq psimb_txt (getpoint "\nPonto de Inserção..."))
      (cn7_txsimb cn7_txtsty "bl" (rtos txt_resto 2 txt_dec) getsty_col getsty_lay 0)
    );progn
    (progn
      (princ "Selecione o texto a receber o resultado...")
      (setq ent2 (entsel))
      (setq new (cons 1 (rtos txt_resto 2 txt_dec)))
      (entmod (subst new (assoc 1 (entget (car ent2))) (entget (car ent2))))
    );progn
  );if
  (devolve)
  (princ)
)

;multiplicação de textos
(defun c:mult ()
  (cn7_init)
  (guarda '("blipmode" "cecolor" "celtype" "clayer" "cmdecho" "orthomode"
          "textstyle" "luprec" "osmode" ))
  (setq cn7_dzin (getvar "dimzin"))
  (prompt "\nSelecione os textos a serem multiplicados...")
  (setq s1 (ssget '((0 . "TEXT"))))
  (setq txt_dec (getint "\nNúmero de casas decimais do resultado...<Enter = 0>..."))
  (if (= nil txt_dec) (setq txt_dec 0))
  (setvar "dimzin" 1)
  (setq s1_len (sslength s1) counter 0 txt_mult 1.00)
  (repeat s1_len
    (setq curr_ent (ssname s1 counter))
    (if (distof (cdr (assoc 1 (entget curr_ent))))
      (progn
	(setq txt_mult (* txt_mult (distof (cdr (assoc 1 (entget curr_ent))))))
	(setq counter (1+ counter))
      )
      (setq counter (1+ counter))
    )
  );repeat
  (prompt (strcat "Produto = " (rtos txt_mult 2 2)))
  (initget 1 "Escrever Modificar")
  (setq resp (getkword "\nEscrever ou Modificar texto existente ? <E ou M> "))
  (if (= resp "Escrever")
    (progn
      (cn7_getstyle)
      (cn7_text_hfinal)
      (cn7_text_height)
      (setq psimb_txt (getpoint "\nPonto de Inserção..."))
      (cn7_txsimb cn7_txtsty "bl" (rtos txt_mult 2 txt_dec) getsty_col getsty_lay 0)
    );progn
    (progn
      (princ "Selecione o texto a receber o resultado...")
      (setq ent2 (entsel))
      (setq new (cons 1 (rtos txt_mult 2 txt_dec)))
      (entmod (subst new (assoc 1 (entget (car ent2))) (entget (car ent2))))
    );progn
  );if
  (devolve)
  (princ)
)

;divisão de textos
(defun c:divi ()
  (cn7_init)
  (guarda '("blipmode" "cecolor" "celtype" "clayer" "cmdecho" "orthomode"
          "textstyle" "luprec" "osmode" ))
  (setq cn7_dzin (getvar "dimzin"))
  ;dividendo
  (setq dividendo (entsel "\nSelecione o primeiro texto (Dividendo)..."))
  (if (= nil dividendo) (exit))
  (if (/= "TEXT" (cdr (assoc 0 (entget (car dividendo)))))
    (progn
      (alert "\nObjeto selecionado não é um texto...")
      (exit)
    )
    (progn
      (if (not (distof (cdr (assoc 1 (entget (car dividendo))))))
	(progn
	  (alert "\nO texto selecionado não corresponde a um número...")
	  (exit)
	)
      )
    )
  )
  (setq txt_dividendo (distof (cdr (assoc 1 (entget (car dividendo))))))

  ;divisor
  (setq divisor (entsel "\nSelecione o segundo texto (Divisor)..."))
  (if (= nil divisor) (exit))
  (if (/= "TEXT" (cdr (assoc 0 (entget (car divisor)))))
    (progn
      (alert "\nObjeto selecionado não é um texto...")
      (exit)
    )
    (progn
      (if (not (distof (cdr (assoc 1 (entget (car divisor))))))
	(progn
	  (alert "\nO texto selecionado não corresponde a um número...")
	  (exit)
	)
      )
    )
  )
  (setq txt_divisor (distof (cdr (assoc 1 (entget (car divisor))))))
  (setq txt_dec (getint "\nNúmero de casas decimais do resultado...<Enter = 0>..."))
  (if (= nil txt_dec) (setq txt_dec 0))
  (setvar "dimzin" 1)
  (setq txt_quociente (/ txt_dividendo txt_divisor))
  (prompt (strcat "Quociente = " (rtos txt_quociente 2 2)))
  (initget 1 "Escrever Modificar")
  (setq resp (getkword "\nEscrever ou Modificar texto existente ? <E ou M> "))
  (if (= resp "Escrever")
    (progn
      (cn7_getstyle)
      (cn7_text_hfinal)
      (cn7_text_height)
      (setq psimb_txt (getpoint "\nPonto de Inserção..."))
      (cn7_txsimb cn7_txtsty "bl" (rtos txt_quociente 2 txt_dec) getsty_col getsty_lay 0)
    );progn
    (progn
      (princ "Selecione o texto a receber o resultado...")
      (setq ent2 (entsel))
      (setq new (cons 1 (rtos txt_quociente 2 txt_dec)))
      (entmod (subst new (assoc 1 (entget (car ent2))) (entget (car ent2))))
    );progn
  );if
  (devolve)
  (princ)
)

;solicita mum estilo e veryfica se é válido
(defun cn7_getstyle ()
  (setq cn7_txtsty (strcase (getstring "\nEstilo de Texto...<ENTER=R80>...")))
  (if (or (= "" cn7_txtsty) (= nil cn7_txtsty)) (setq cn7_txtsty "r80"))
  (if (not (tblsearch "style" cn7_txtsty))
    (progn
      (alert "Estilo escolhido não existe!\nVerifique a digitação ou\nDigite <CFG> para criá-lo...")
      (exit)
    )
  )
  (cn7_altext_readfile)
  (cond
    ((= cn7_txtsty "R50") (setq getsty_lay "txt_r50" getsty_col 1))
    ((= cn7_txtsty "R60") (setq getsty_lay "txt_r60" getsty_col 1))
    ((= cn7_txtsty "R70") (setq getsty_lay "txt_r70" getsty_col 2))
    ((= cn7_txtsty "R80") (setq getsty_lay "txt_r80" getsty_col 2))
    ((= cn7_txtsty "R90") (setq getsty_lay "txt_r90" getsty_col 3))
    ((= cn7_txtsty "R100") (setq getsty_lay "txt_r100" getsty_col 3))
    ((= cn7_txtsty "R120") (setq getsty_lay "txt_r100" getsty_col 4))
    ((= cn7_txtsty "R140") (setq getsty_lay "txt_r100" getsty_col 5))
    ((= cn7_txtsty "R175") (setq getsty_lay "txt_r100" getsty_col 6))
    ((= cn7_txtsty "R200") (setq getsty_lay "txt_r100" getsty_col 6))
    ((= cn7_txtsty "T1") (setq getsty_lay "txt_t1" getsty_col (fix (distof t1_col))))
    ((= cn7_txtsty "T2") (setq getsty_lay "txt_t2" getsty_col (fix (distof t2_col))))
    ((= cn7_txtsty "T3") (setq getsty_lay "txt_t3" getsty_col (fix (distof t3_col))))
    ((= cn7_txtsty "T4") (setq getsty_lay "txt_t4" getsty_col (fix (distof t4_col))))
    ((= cn7_txtsty "T5") (setq getsty_lay "txt_t5" getsty_col (fix (distof t5_col))))
    ((= cn7_txtsty "T6") (setq getsty_lay "txt_t6" getsty_col (fix (distof t6_col))))
    ((= cn7_txtsty "T7") (setq getsty_lay "txt_t7" getsty_col (fix (distof t7_col))))
    (t (setq getsty_lay "txt_r80" getsty_col 2))
  )
)
  
;caracteres especiais
(defun c:espec ()
  (setq dcl_id (load_dialog (strcat cnp_root "/lisp/cadnorma.dcl")))
  (if (not (new_dialog "cn7_txt_espec" dcl_id)) (exit))
  (setq x (dimx_tile "cn7_txt_espec_image")
	y (dimy_tile "cn7_txt_espec_image"))
  (start_image "cn7_txt_espec_image")
  (slide_image 0 0 x y (strcat cnp_root "/slides/txt_espec.sld"))
  (end_image)
  (setq txt_espec_dcl (start_dialog))
  (unload_dialog dcl_id)
  (princ)
)

;copia e edita
(defun c:cped ()
  (prompt "\nSelecione o texto a ser copiado...")
  (setq ent1 (entget (car (entsel))))
  (command "._copy" (cdr (assoc -1 ent1)) "" "_non" (cdr (assoc 10 ent1))
	   (getpoint (cdr (assoc 10 ent1)) "\nPonto onde copiar...")
	   "._ddedit" "_l" "")
  (princ)
)


;Texto para Texto
(defun c:tpt ()
  (prompt "\nSelecione o texto para ser copiado...")
  (setq s1 (entsel)
	s1_text (cdr (assoc 1 (entget (car s1))))
	new (cons 1 s1_text)
  )
  (prompt "\nSelecione os textos a serem alterados...")
  (setq s1 (ssget '((0 . "TEXT")))
	s1_n (sslength s1)
	counter 0)
  (repeat s1_n
    (setq s2 (ssname s1 counter))
    (entmod (subst new (assoc 1 (entget s2)) (entget s2)))
    (setq counter (1+ counter))
  )
  (princ)
)

;troca texto
(defun c:tct ()
  (prompt "\nSelecione o primeiro texto...")
  (setq s1 (entsel)
	s1_text (cdr (assoc 1 (entget (car s1))))
	new1 (cons 1 s1_text)
  )
  (prompt "\nSelecione o segundo texto...")
  (setq s2 (entsel)
	s2_text (cdr (assoc 1 (entget (car s2))))
	new2 (cons 1 s2_text)
  )
  (entmod (subst new2 (assoc 1 (entget (car s1))) (entget (car s1))))
  (entmod (subst new1 (assoc 1 (entget (car s2))) (entget (car s2))))
  (princ)
)


;Concatenacao de Textos
(defun c:cat ()
    (prompt "\nSelecione o primeiro texto a ser lido...")
    (setq ent1 (entget (car (entsel))))
    (prompt "\nSelecione o texto a ser acrescentado...")
    (setq ent2 (entget (car (entsel))))
    (setq txt1 (cdr (assoc 1 ent1)))
    (setq txt2 (cdr (assoc 1 ent2)))
    (setq txt3 (strcat txt1 " " txt2))
    (setq newtxt (cons 1 txt3))
    (setq old (assoc 1 ent1))
    (entmod (subst newtxt old ent1))
  (princ)
);defun


;novo caixa alta
(defun c:cxa ()
  (prompt "\nSelecione os textos a serem transformados para maiúsculas...")
  (setq s1 (ssget '((0 . "TEXT"))))
  (setq count_limit (sslength s1) counter 0)
  (repeat count_limit
    (setq ent1 (entget (ssname s1 counter)))
    (setq new (cons 1 (strcase (cdr (assoc 1 ent1)))))
    (setq ent1 (entmod (subst new (assoc 1 ent1) ent1)))
    (setq counter (1+ counter))
  );repeat  
  (princ)
)


;novo caixa baixa
(defun c:cxb ()
  (prompt "\nSelecione os textos a serem transformados para minúsculas...")
  (setq s1 (ssget '((0 . "TEXT"))))
  (setq count_limit (sslength s1) counter 0)
  (repeat count_limit
    (setq ent1 (entget (ssname s1 counter)))
    (setq new (cons 1 (strcase (cdr (assoc 1 ent1)) "t")))
    (setq ent1 (entmod (subst new (assoc 1 ent1) ent1)))
    (setq counter (1+ counter))
  );repeat  
  (princ)
)


;decimais de textos        
(defun c:txd ()
  (setq tx_dec (getint "\nEntre com o número de casas dedimais desejado...<Enter = 0>..."))
  (if (= nil tx_dec) (setq tx_dec 0))
  (prompt "\nSelecione os textos a serem transformados...")
  (setq tx_s1 (ssget '((0 . "TEXT"))))
  (setq tx_s1n (sslength tx_s1) counter 0)
  (repeat tx_s1n
    (setq tx_ent (entget (ssname tx_s1 counter)))
    (setq tx_txt (assoc 1 tx_ent))
    (if (and (/= nil tx_txt) (distof (cdr tx_txt)))
      (progn
	(setq cn7_dzin (getvar "dimzin"))
	(setvar "dimzin" 1)
	(setq tx_new (cons 1 (rtos (atof (cdr tx_txt)) 2 tx_dec)))
	(entmod (subst tx_new tx_txt tx_ent))
	(setvar "dimzin" cn7_dzin)
      );progn
    );
    (setq counter (1+ counter))
  );repeat
 (princ) 
)

;acrescenta prefixos e/ou sufixos a textos
(defun c:presufix ()
	(setq txt_prefix (getstring T "\nEntre com o prefixo..."))
  	(setq txt_sufix (getstring T "\nEntre com o sufixo..."))
  	(while (/= nil (setq s1_txt (ssget)))
	  	(setq counter 0)
	  	(while (/= nil (setq curr_ent (ssname s1_txt counter)))
		  	(if (= (strcase "text") (cdr (assoc 0 (entget curr_ent))))
			  (progn
			  	(setq new (cons 1 (strcat txt_prefix (cdr (assoc 1 (entget curr_ent))) txt_sufix)))
			  	(setq old (assoc 1 (entget curr_ent)))
			  	(entmod (subst new old (entget curr_ent)))
			  	(setq counter (1+ counter))
			  );progn
			  (setq counter (1+ counter))
			);if
		  );while
	);while
  (princ)
);defun


;escreve o nome do desenho atual
(defun c:dwg ()
  (cn7_init)
  (guarda '("blipmode" "cecolor" "celtype" "clayer" "cmdecho" "orthomode"
          "textstyle" "luprec" "osmode" ))
  (initget "Escrever Modificar")
  (setq resp (getkword "\nModificar/<Escrever>? "))
  (if (= resp nil) (setq resp "Escrever"))
  (if (= resp "Escrever")
    (progn
      (cn7_getstyle)
      (cn7_text_hfinal)
      (cn7_text_height)
      (setq psimb_txt (getpoint "\nPonto de Inserção..."))
      (cn7_txsimb cn7_txtsty "bl" (getvar "dwgname") getsty_col getsty_lay 0)
    );progn
    (progn
      (princ "Selecione o texto a modificar.")
      (setq ent2 (entsel))
      (setq new (cons 1 (getvar "dwgname")))
      (entmod (subst new (assoc 1 (entget (car ent2))) (entget (car ent2))))
    );progn
  );if
  (devolve)
  (princ)
)

;escreve a data atual
(defun c:data ()
  (cn7_init)
  (guarda '("blipmode" "cecolor" "celtype" "clayer" "cmdecho" "orthomode"
          "textstyle" "luprec" "osmode" ))
  (setq date_cod (rtos (fix (getvar "cdate")) 2 0))
  (setq curr_date (strcat (substr date_cod 7 2) "/" (substr date_cod 5 2) "/" (substr date_cod 1 4)))
  (initget "Escrever Modificar")
  (setq resp (getkword "\nModificar/<Escrever>? "))
  (if (= resp nil) (setq resp "Escrever"))
  (if (= resp "Escrever")
    (progn
      (cn7_getstyle)
      (cn7_text_hfinal)
      (cn7_text_height)
      (setq psimb_txt (getpoint "\nPonto de Inserção..."))
      (cn7_txsimb cn7_txtsty "bl" curr_date getsty_col getsty_lay 0)
    );progn
    (progn
      (princ "Selecione o texto a modificar.")
      (setq ent2 (entsel))
      (setq new (cons 1 curr_date))
      (entmod (subst new (assoc 1 (entget (car ent2))) (entget (car ent2))))
    );progn
  );if
  (devolve)
  (princ)
)

;cnp_09


    
;***************************
;comandos de dimensionamento
;***************************

;funções auxiliares

;encontra dimscale / define Layer
(defun cn7_dim_scllay  ()
  (cn7_init)
  (setq grp_type "2")
  (cn7_find_blkscl)
  (cond
    ((and (= cdn_dim 1) (= (getvar "dimstyle") "cadnorma_dim1")) (cn7_verylayer (strcat cn7_blk_prefixlay "dim1") 1))    
    ((and (= cdn_dim 1) (= (getvar "dimstyle") "cadnorma_dim2")) (cn7_verylayer (strcat cn7_blk_prefixlay "dim2") 1))
    ((and (= cdn_dim 1) (= (getvar "dimstyle") "cadnorma_dim3")) (cn7_verylayer (strcat cn7_blk_prefixlay "dim3") 1))
    ((and (= cus_dim 1) (= (getvar "dimstyle") "cadnorma_dim4")) (cn7_verylayer (strcat cn7_blk_prefixlay "dim4") 1))
    ((and (= cus_dim 1) (= (getvar "dimstyle") "cadnorma_dim5")) (cn7_verylayer (strcat cn7_blk_prefixlay "dim5") 1))
  )
  (if (= 1 (getvar "tilemode"))
    (progn
      (setvar "dimscale" (/ (* cn7_msscl cn7_dwgunit) 1000 ))
      (setvar "dimlfac" (* (/ cn7_dimunit cn7_dwgunit) scdim_newscale))
      (if (/= 1.0 scdim_newscale)
	(prompt (strcat "Atenção! Cotas multiplicadas por " (rtos scdim_newscale 2 2) "..."))
      )
    )
    (progn
      (setvar "dimscale" 0.0)
      (setvar "dimlfac" 1.0)
    )
  )
  (princ)
);defun


;verifica a existência do 'Dimstyle'
(defun cn7_dim_style (cn7_dim_style_name)
  (if (tblsearch "dimstyle" cn7_dim_style_name)
    (command "._dimstyle" "_r" cn7_dim_style_name)
    (progn
      (alert (strcat "Dimstyle '" cn7_dim_style_name "' não encontrado!\nDigite 'CFG' para configurar..."))
      (exit)
    )
  )
)

;dimlinear
(defun c:dl  ()
  (cn7_dim_style "cadnorma_dim1")
  (setvar "dimsah" 0)
  (cn7_dim_scllay)
  (command "._dimlinear")
  (princ)
)

(defun c:dl2  ()
  (cn7_dim_style "cadnorma_dim4")
  (setvar "dimsah" 0)
  (cn7_dim_scllay)
  (command "._dimlinear")
  (princ)
)

;dimaligned
(defun c:dn  ()
  (cn7_dim_style "cadnorma_dim1")
  (setvar "dimsah" 0)
  (cn7_dim_scllay)
  (command "._dimaligned")
  (princ)
)

(defun c:dn2  ()
  (cn7_dim_style "cadnorma_dim4")
  (setvar "dimsah" 0)
  (cn7_dim_scllay)
  (command "._dimaligned")
  (princ)
)

;quickdim
(defun c:qd  ()
  (cn7_dim_style "cadnorma_dim1")
  (setvar "dimsah" 0)
  (cn7_dim_scllay)
  (command "._qdim")
  (princ)
)

(defun c:qd2  ()
  (cn7_dim_style "cadnorma_dim4")
  (setvar "dimsah" 0)
  (cn7_dim_scllay)
  (command "._qdim")
  (princ)
)

;dim radial
(defun c:dr  ()
  (cn7_dim_style "cadnorma_dim2")
  (cn7_dim_scllay)
  (setvar "dimsah" 0)
  (command "._dimradius")
  (princ)
)

(defun c:dr2  ()
  (cn7_dim_style "cadnorma_dim5")
  (cn7_dim_scllay)
  (setvar "dimsah" 0)
  (command "._dimradius")
  (princ)
)

;dim diametro
(defun c:dd  ()
  (cn7_dim_style "cadnorma_dim2")
  (cn7_dim_scllay)
  (setvar "dimsah" 0)
  (command "._dimdiameter")
  (princ)
)

(defun c:dd2  ()
  (cn7_dim_style "cadnorma_dim5")
  (cn7_dim_scllay)
  (setvar "dimsah" 0)
  (command "._dimdiameter")
  (princ)
)

;dim angular
(defun c:dg  ()
  (cn7_dim_style "cadnorma_dim2")
  (cn7_dim_scllay)
  (setvar "dimsah" 0)
  (command "._dimangular")
  (princ)
)

(defun c:dg2  ()
  (cn7_dim_style "cadnorma_dim5")
  (cn7_dim_scllay)
  (setvar "dimsah" 0)
  (command "._dimangular")
  (princ)
)

;dim leader
(defun c:dld ()
  (cn7_dim_style "cadnorma_dim1")
  (cn7_dim_scllay)
  (setvar "dimsah" 0)
  (command "._leader")
  (princ)
)

;dim leader
(defun c:dld2 ()
  (cn7_dim_style "cadnorma_dim5")
  (cn7_dim_scllay)
  (setvar "dimsah" 0)
  (command "._dim1" "_leader")
  (princ)
)

;dim Center
(defun c:dce ()
  (cn7_dim_style "cadnorma_dim1")
  (cn7_dim_scllay)
  (setvar "dimsah" 0)
  (command "._dimcenter")
  (princ)
)

(defun c:dce2 ()
  (cn7_dim_style "cadnorma_dim4")
  (cn7_dim_scllay)
  (setvar "dimsah" 0)
  (command "._dimcenter")
  (princ)
)

;dim quickleader
(defun c:ql  ()
  (cn7_dim_style "cadnorma_dim1")
  (cn7_dim_scllay)
  (setvar "dimsah" 0)
  (command "._qleader")
  (princ)
)

(defun c:ql2  ()
  (cn7_dim_style "cadnorma_dim4")
  (cn7_dim_scllay)
  (setvar "dimsah" 0)
  (command "._qleader")
  (princ)
)

;dimension para apresentação
(defun c:dl1 ()
  (cn7_dim_style "cadnorma_dim3")
  (setvar "dimsah" 0)
  (setvar "dimtofl" 0)
  (cn7_dim_scllay)
  (command "._dimlinear")
  (princ)
)	


(defun c:dn1 ()
  (cn7_dim_style "cadnorma_dim3")
  (setvar "dimsah" 0)
  (setvar "dimtofl" 0)
  (cn7_dim_scllay)
  (command "._dimaligned")
  (princ)
)


;funções que não dependem do dimstyle
(defun c:db  () (cn7_dim_scllay) (setvar "dimsah" 0) (command "._dimbaseline")(princ))
(defun c:dc  () (cn7_dim_scllay) (setvar "dimsah" 0) (command "._dimcontinue")(princ))
(defun c:dc2  () (cn7_dim_scllay) (setvar "dimsah" 0) (command "._dimcontinue")(princ))
(defun c:dte () (command "._dim1" "_tedit")(princ))

;atualização de cotas
(defun c:du  ()
  (cn10_seldim)
  (setq dimstymo (getvar "dimstyle"))
  (command "dimstyle" "r" "cadnorma_dim1")
  (cn7_dim_scllay)
  (command "._dim1" "_up" dim1_sel "")
  (command "dimstyle" "r" "cadnorma_dim2")
  (cn7_dim_scllay)
  (command "._dim1" "_up" dim2_sel "")
  (command "dimstyle" "r" "cadnorma_dim3")
  (cn7_dim_scllay)
  (command "._dim1" "_up" dim3_sel "")
  (command "dimstyle" "r" "cadnorma_dim4")
  (cn7_dim_scllay)
  (command "._dim1" "_up" dim4_sel "")
  (command "dimstyle" "r" "cadnorma_dim5")
  (cn7_dim_scllay)
  (command "._dim1" "_up" dim5_sel "")
  (if (/= 0 (sslength dim0_sel)) (cn10_dimupd_sty))
  (command "dimstyle" "r" dimstymo)
  (princ)
)

;escolhe o estilo de cota para não padronizadas
(defun cn10_dimupd_sty()
  (setq dcl_id (load_dialog (strcat cnp_root "/lisp/cadnorma.dcl")))
  (if (not (new_dialog "cn10_dumup_sty" dcl_id)) (exit))
  (setq dimup_sty "dimup_sty_radio1")
  (set_tile "dimup_sty_radio" "dimup_sty_radio1")
  (action_tile "dimup_sty_radio" "(setq dimup_sty $value)")
  (action_tile "cancel" "(done_dialog 0)")
  (action_tile "accept" "(done_dialog 1)")
  (setq cn10_dimup_dcl (start_dialog))
  (unload_dialog dcl_id)
  (if (= cn10_dimup_dcl 1)
    (cond
      ((= dimup_sty "dimup_sty_radio1")
       (command "dimstyle" "r" "cadnorma_dim1")
       (cn7_dim_scllay)
       (command "._dim1" "_up" dim0_sel "")
      )
      ((= dimup_sty "dimup_sty_radio2")
       (command "dimstyle" "r" "cadnorma_dim4")
       (cn7_dim_scllay)
       (command "._dim1" "_up" dim0_sel "")
      )
    )
  )
)


;*********************************************************************
;identifica cotas editadas
;*********************************************************************
(defun c:iedim ()
  (setq grp_type "2")
  (cn7_find_blkscl)
  (setq s1 (ssget '((0 . "DIMENSION")))
	s1_len (sslength s1)
	counter 0)
  (command "._undo" "_m")
  (repeat s1_len
    (setq ent1 (ssname s1 counter)
	  ent1_list (entget ent1)
	  ent1_value (cdr (assoc 1 ent1_list))
	  ent1_txpoint (cdr (assoc 11 ent1_list))
    )
    (if (/= "" ent1_value)
      (command "._insert" (strcat cnp_root "/blocos/dimtool_iedim") "_s" cn7_blkscl "_non" ent1_txpoint 0)
    )
    (setq counter (1+ counter))
  )
  (prompt "\nUse o comando <UB> para retornar... ")
  (princ)
)

;*********************************************************************
;seleciona um conjunto de dimensions e separa por estilos
;*********************************************************************
(defun cn10_seldim ()
  (setq s1 (ssget (list (cons 0 "DIMENSION")))
	s1_len (sslength s1)
	dim0_sel (ssadd)
	dim1_sel (ssadd)
	dim2_sel (ssadd)
	dim3_sel (ssadd)
	dim4_sel (ssadd)
	dim5_sel (ssadd)
	counter 0
  )
  (repeat s1_len
    (setq ent (ssname s1 counter)
	  ent_list (entget ent)
	  ent_dimtype (cdr (assoc 3 ent_list)))
    (cond
      ((= (strcase ent_dimtype t) "cadnorma_dim1") (setq dim1_sel (ssadd ent dim1_sel)))
      ((= (strcase ent_dimtype t) "cadnorma_dim2") (setq dim2_sel (ssadd ent dim2_sel)))
      ((= (strcase ent_dimtype t) "cadnorma_dim3") (setq dim3_sel (ssadd ent dim3_sel)))
      ((= (strcase ent_dimtype t) "cadnorma_dim4") (setq dim4_sel (ssadd ent dim4_sel)))
      ((= (strcase ent_dimtype t) "cadnorma_dim5") (setq dim5_sel (ssadd ent dim5_sel)))
      (t (setq dim0_sel (ssadd ent dim0_sel)))
    )
    (setq counter (1+ counter))
  )
  (if (or
	(not (tblsearch "dimstyle" "cadnorma_dim1"))
	(not (tblsearch "dimstyle" "cadnorma_dim2"))
	(not (tblsearch "dimstyle" "cadnorma_dim3"))
	(not (tblsearch "dimstyle" "cadnorma_dim4"))
	(not (tblsearch "dimstyle" "cadnorma_dim5"))
      )
    (progn
      (alert "Estilo de cota inexistente...\nUse o comando 'CFG' para criá-los...")
      (exit)
    )
  )
)

;cnp_10


;******************************************************************************
;******************************************************************************
;Utilidades
;******************************************************************************
;******************************************************************************

;************ Funcao M2P *************
(defun c:m2p ()
  (setq p1 (getpoint "\nPrimeiro Ponto: "))
  (setq P2 (GETPOINT P1 "\nSegundo Ponto: "))
  (setq osmo (getvar "osmode"))
  (setvar "osmode" 0)
  (setq p3 (POLAR P1 (ANGLE P1 P2) (/ (DISTANCE P1 P2) 2)))
  (command p3)
  (setvar "osmode"osmo)
  (princ)
)

;seta tipo 1
(defun c:st1 ()
  (guarda '("blipmode" "cecolor" "celtype" "clayer" "cmdecho" "orthomode"
          "textstyle" "luprec" "osmode" ))
  (setvar "cmdecho" 0)
  (setq grp_type "2")
  (cn7_find_blkscl)
  (setvar "cmdecho" 0)
  (prompt "\nIndique o ponto de inserção e depois a rotação...")
  (command "._insert" (strcat cnp_root "/blocos/util_st1") "_scale" cn7_blkscl)
  (devolve)
  (setq grp_type nil)
  (princ)
)

;seta tipo 2
(defun c:st2 ()
  (guarda '("blipmode" "cecolor" "celtype" "clayer" "cmdecho" "orthomode"
          "textstyle" "luprec" "osmode" ))
  (setvar "cmdecho" 0)
  (setq grp_type "2")
  (cn7_find_blkscl)
  (setvar "cmdecho" 0)
  (prompt "\nIndique o ponto de inserção e depois a rotação...")
  (command "._insert" (strcat cnp_root "/blocos/util_st2") "_scale" cn7_blkscl)
  (devolve)
  (setq grp_type nil)
  (princ)
)

;salva seleção anterior
(defun c:ssa () (setq ss (ssget "p"))(princ))

(defun c:ssn ()
  (prompt "\nSelecione os objetos a serem guardados em uma seleção (ss)...")
  (setq ss (ssget))
)

;gravar e recuperar vistas
(defun c:gv1 ()
  (command "._view" "_s" "cnp_v1")
  (princ)
)

(defun c:gv2 ()
  (command "._view" "_s" "cnp_v2")
  (princ)
)

(defun c:rv1 ()
  (command "._view" "_r" "cnp_v1")
  (princ)
)

(defun c:rv2 ()
  (command "._view" "_r" "cnp_v2")
  (princ)
)



;Le a cor de uma entidade base e copia para outras selecionadas
(defun c:cpc (/ p x s2)
  (prompt "Selecione a cor basica...")
  (setq e_color(cdr (assoc 62 (entget (car (entsel))))))
  (prompt "\nSelecione as Entidades a serem Transformadas")
  (setq s2 (ssget))
  (command "._chprop" s2 "" "_c" e_color "")
  (princ)
)

;Muda a cor e o tipo de linha de entidades selecionadas para BYLAYER
(defun c:by ()
  (prompt "\nSelecione as entidaddes para assumirem cor e tipo de linha BYLAYER...")
  (setq s1 (ssget))
  (command "._chprop" s1 "" "_c" "bylayer" "_lt" "bylayer" "")
  (princ)
);defun


;cnp_11


;Funcao MRT (Move-Rotate)
(defun c:mr (/ ss1 p1)
 (if (setq ss1 (ssget))
  (progn
   (setq p1 (getpoint "\nPonto base: "))
   (prompt "\nPonto destino: ")
   (command "._move" ss1 "" "_non" p1 "_non" p1 "._point" "_non" p1 "._move" ss1 (entlast) "" "_non" p1 pause)
   (prompt "\nÂngulo de rotação: ")
   (command "._rotate" ss1 "" (cdr (assoc 10 (entget (entlast)))) pause "._redraw")
  )
 )
 (command "._erase" "_l" "")
 (princ)
 )

;Funcao CR (Copy-Rotate)
(defun c:cr (/ ss1 p1)
 (prompt "\nSelecione os objetos a copiar e depois rotacionar... ")
 (if (setq ss1 (ssget))
  (progn
   (setq p1 (getpoint "\nPonto base: "))
   (prompt "\nPonto de destino...")
   (command "._copy" ss1 "" "_non" p1 "_non" p1 "._point" "_non" p1 "._move" ss1 (entlast) "" "_non" p1 pause)
   (prompt "\nÂngulo de rotação: ")
   (command "._rotate" ss1 "" (cdr (assoc 10 (entget (entlast)))) pause "._redraw")
  )
 )
 (command "._erase" "_l" "")
  (princ)
)

;fução copy_scale
(defun c:csc (/ ss1 p1)
 (prompt "\nSelecione os objetos a copiar e depois escalar... ")
 (if (setq ss1 (ssget))
  (progn
   (setq p1 (getpoint "\nPonto base: "))
   (setq p2 (getpoint p1 "\nSegundo ponto ou <ENTER> para o mesmo ponto..."))
   (if (= nil p2) (setq p2 p1))
   (setq csc_factor (getreal "\nFator de Escala: "))
   (command  "._copy" ss1 "" "_non" p1 "_non" p1  "._move" "_p" "" "_non" p1 "_non" p2 "._scale" ss1 "" "_non" p2 csc_factor)
  )
 )
  (princ)
)


;stretch com Crossing Poligonal
(defun c:stc () (command "._stretch" "_cp"))

;Fillet com Raio Zero
(defun c:f0  ()
  (setvar "filletrad" 0.0)
  (command "._fillet")
)

;função Scale - Circle
(defun c:scc ()
  (setq s1 (ssget '((0 . "CIRCLE")))
	s1_len (sslength s1)
	counter 0)
  (initget 128)
  (setq scc_txfactor (getstring "\nReferência/<Fator de Escala>... "))
  (if (not (setq scc_factor (distof scc_txfactor)))
    (progn
      (if (= "R" (strcase scc_txfactor))
	(setq scc_refdist (getdist "\nValor de Referência...: ")
	      scc_newdist (getdist "\nNovo Valor...: ")
	      scc_factor (/ scc_refdist scc_newdist))
	(progn
	  (alert "Valor inválido!\nEntre com o fator de escala,\nou digite 'R' para referência!")
	  (exit)
	)
      )
     )
  )
  (repeat s1_len
    (setq e1 (ssname s1 counter)
	  e1_list (entget e1)
	  e1_radius (cdr (assoc 40 e1_list))
	  e1_list (entmod (subst (cons 40 (* e1_radius scc_factor)) (assoc 40 e1_list) e1_list)))
    (setq counter (1+ counter))
  )
  (princ)
)

;break em 1 ponto
(defun c:b1  ()
  (prompt "\nQuebra num ponto...Selecione uma entidade e um ponto...")
  (command "._break" pause "_f" pause "@")
  (princ)
)

;break em 2 pontos
(defun c:b2  ()
  (prompt "\nQuebra entre dois pontos...Selecione uma entidade e dois pontos...")
  (command "._break" pause "_f")
  (princ)
)

;comando Split : offest para os dois lados (modificado por bricscad)
(defun c:split (/ ang end1 ent pt test)
  (setvar "cmdecho" 0)
  (if (= nil ds)
    (progn
      (setq ds (getreal "\nDistância (offset)... "))
      (if (= nil ds) (exit))
    )
    (progn
      (setq ds1 (getreal (strcat "\nDistância (offset)...<" (rtos ds 2 2) ">... ")))
      (if (/= nil ds1) (setq ds ds1))
    )
  )
  (while (setq ent (entsel "\nSelecione a linha:  "))
     (setq end1 (osnap (cadr ent) "end"))
     (setq ang (angle end1 (cadr ent)))
     (initget "center,c CENTER,C")
     (setq pt (getpoint "\nLado do offset/<Centro>:  "))
     (setq pt (if pt pt "C"))
     (command "._offset")
     (if (listp pt)
        (command ds ent "_non" pt "")
        (progn
           (command (/ ds 2) ent "_non" (polar (cadr ent) (+ ang (/ pi 2)) ds)
                             ent "_non" (polar (cadr ent) (- ang (/ pi 2)) ds)
                             ""
           )
           (entdel (car ent))
  ) ) )
  (princ)
)

;;;(defun c:split (/ ang end1 ent pt test)
;;;  (setvar "cmdecho" 0)
;;;  (if (= nil ds)
;;;    (progn
;;;      (setq ds (getreal "\nDistância (offset)... "))
;;;      (if (= nil ds) (exit))
;;;    )
;;;    (progn
;;;      (setq ds1 (getreal (strcat "\nDistância (offset)...<" (rtos ds 2 2) ">... ")))
;;;      (if (/= nil ds1) (setq ds ds1))
;;;    )
;;;  )
;;;  (while (setq ent (entsel "\nSelecione a linha:  "))
;;;     (setq end1 (osnap (cadr ent) "end"))
;;;     (setq ang (angle end1 (cadr ent)))
;;;     (initget "center,c CENTER,C")
;;;     (setq pt (getpoint "\nLado do offset/<Centro>:  "))
;;;     (setq pt (if pt pt "C"))
;;;     (command "._offset")
;;;     (if (listp pt)
;;;        (command ds ent pt "")
;;;        (progn
;;;           (command (/ ds 2) ent (polar (cadr ent) (+ ang (/ pi 2)) ds)
;;;                             ent (polar (cadr ent) (- ang (/ pi 2)) ds)
;;;                             ""
;;;           )
;;;           (entdel (car ent))
;;;  ) ) )
;;;  (princ)
;;;)


(defun c:set (/)
  (setq olderr *error*)
  (setq uecho (getvar "cmdecho"))
  (setvar "cmdecho" 0)
  (setq ofst2 ofst)
  (if (= ofst nil)
    (setq ofst 0)
  )
  (prompt "\n Distância para Offset <")
  (prin1 ofst)
  (prompt "> :")
  (setq ofst (getdist))
  (if (= ofst nil)
    (setq ofst ofst2)
  )
  (setq x 0)
  (while (< x 1000)
    (setq offit (get_offspec))
    (setq offpnt (getpoint "\nEscolha o lado para offset :"))
    (command "._offset" ofst offit offpnt "")
    (setq ofst3 ofst)
    (setq clay (getvar "CLAYER"))
    (setq lastent (entlast))
    (setq lastinfo (entget lastent))
    (setq
      lastinfo (subst (cons 6 "BYLAYER") (assoc 6 lastinfo) lastinfo)
    )
    (setq lastinfo (subst (cons 62 256) (assoc 62 lastinfo) lastinfo))
    (setq lastinfo (subst (cons 8 clay) (assoc 8 lastinfo) lastinfo))
    (entmod lastinfo)
    (setq x (+ x 1))
  )
  (setq *error* olderr)
  (princ)
)

;Funcao SET -  offset para o layer current
(defun *error* (s)
    (repeat 3 (command))
    (cond (  (member s '("Function cancelled" "console break"))
             (princ "*cancel*"))
          (t (princ (strcat "\nError: " s))))
    (setvar "highlight" 1)
    (setq *error* olderr)
    (princ)
)

(defun get_offspec ( / e d)
   (cond (  (setq e (entsel "\nObjeto para offset/ENTER para nova distância:")))
         (t (setq ofst (xgetdist "\nNova distância" ofst))
            (if (= ofst nil) ;|(setq ofst ofst3))|; (exit))
            (while (not (setq e (entsel "\nObjeto para offset: "))))))
   e
)

(defun xgetdist (msg def)
     (cond (  (getdist (cond (def (strcat msg " <" (rtos ofst) ">:"))
     (t ": ")))))
)


;Funcao MOS - Multiple offset
(defun c:mos ()
  (setq ent1 (entsel))
  (setq pt1 (getpoint "\nPonto para offset..."))
  (command "._offset" "_t" ent1 pt1 "")
  (while (/= nil (setq pt1 (getpoint "\nPonto para offset...")))
    (command "._offset" "_t" ent1 pt1 "")

  )
  (princ)
)


(defun C:DULXTRIM ( / edge linset side setsiz looper)
   (setvar "cmdecho" 0)
   (prompt "\nSelecione os limites de corte:  ")
   (setq edge (ssget))                                ;get the edge
   (prompt "\nSelecione elementos a cortar:  ")
   (setq linset (ssget)                               ;get the lines
         side (getpoint "\nSelecione lado para cortar:  ")     ;get the side
         setsiz (sslength linset)                     ;size of line set
         looper -1                                    ;initialize loop ptr
   )                                                  ;setq calculations
   (command "._trim" edge "")                           ;trim it
   (repeat setsiz                                     ;for all lines
      (setq looper (1+ looper))                       ;increment loop ptr
      (command (list (ssname linset looper) side))
   )                                                  ;repeat
   (command "")

   (setvar "cmdecho" 1)
  (princ)
)                                                     ;defun


(defun c:xtrim (/ p1 p2 e1 edge linset side setsiz looper)
    (setvar "cmdecho" 0)
    (prompt "\nDesenhe a linha cortante:  ")
    (setq p1 (getpoint))
    (setq p2 (getpoint p1))
    (command nil nil nil "._point" "@")
    (setq e1 (entlast))
    (entdel e1)
    (command "._line" "_non" p1 "_non" p2 "")
    (setq edge (entnext e1))
    (prompt "\nIndique os objetos para cortar:  ")
    (setq linset (ssget)
            side (getpoint "\nIndique o lado para cortar:  ")
            setsiz (sslength linset)
            looper -1
    )
    (command "._trim" edge "")
    (repeat setsiz
        (setq looper (1+ looper))
        (command (list (ssname linset looper) side))
    )
    (command "")
    (entdel edge)
    (command "._ortho" "_off")
    (setvar "cmdecho" 1)
    (princ)
)


(defun C:DULXEXTD(/ bou ent pt len cou)
 (setvar "CMDECHO" 0)
 (setq cou -1)                                  ;set counter
 (prompt "\nSelect limitantes ...")          ;prompt user
 (setq bou (ssget))(terpri)(terpri)             ;boundary edge
 (prompt "\nSelect objetos a estender...")
 (setq ent (ssget))(terpri)(terpri)             ;entities
 (setq len (sslength ent))                        ;number of entities
 (setq pt (getpoint "\nClique no lado a estender..."))  ;reference point for extend
 (command "._extend" bou "")                        ;command
 (repeat len
  (setq cou (1+ cou))
  (command (list (ssname ent cou) pt)) 
 )
 (command "")
 (setvar "CMDECHO" 1)
 (prin1)
)                                               ;defun



;* Phanthom extend--extend a line to a "phantom" line
;* which is not existing in drawing.
;* Kent M. Taylor 2/90
;*
(defun c:xte (/ p1 p2 e1 e2 d1)
  (prompt "\nDesenhe a Linha de Estensão: ")
  (setq p1 (getpoint))
  (setq p2 (getpoint p1))
  (command nil nil nil "._point" "@")
  (setq e1 (entlast))
  (entdel e1)
  (command "._line" "_non" p1 "_non" p2 "")
  (setq e2 (entnext e1))
   (while
    (setq d1 (entsel "\nSelecione objeto a estender: "))
    (command "._extend" e2 "" d1 "")
   );while
  (entdel e2)
  (command "._ortho" "_off")
 (princ)
)

;cnp_12


;***************************************************************
;Convenções Gráficas
;***************************************************************

;eixo de projeto
(defun c:eixp ()
  (guarda '("blipmode" "cecolor" "celtype" "clayer" "cmdecho" "orthomode"
          "textstyle" "luprec" "osmode" ))
;;;  (setq eixp_name (getstring "\nNome do Eixo...: "))
  (if (= "" eixp_name)
    (progn
      (alert "O nome do eixo não pode ser nulo!")
      (exit)
    )
  )
  (setq eixp_eixo_ltlist
	 (list "Center" "Center2" "Phantom" "Phantom2"
	       "Dashdot" "Dashdot2" "Divide" "Divide2" "Continuous")
  )
  (setq eixp_text_stylist
	 (list "r50" "r60" "r70" "r80" "r90" "r100" "r120" "r140" "r175" "r200"
			    "t1" "t2" "t3" "t4" "t5" "t6" "t7")
  )
  (eixp_file)
  (eixp_action)
  (devolve)
  (princ)
)

;carburador
(defun eixp_action ()
  (initget 128)
  (setq pt1 (getpoint "\nFormatar/<Centro do círculo...>:"))
  (cond
    ;se clicar num ponto
    ((= 'LIST (type pt1))
     (eixp_draw))
    ((= 'STR  (type pt1))
     (cond
       ((= "F" (strcase pt1))
	(eixp_format)
       )
       (t
	(prompt "\nOpção inválida... Marque o ponto ou digite <F> para Formatar...")
	(eixp_action)
       )
     )
    )
  )
)

;formata os itens de eixo
(defun eixp_format ()
  (setq dcl_id (load_dialog (strcat cnp_root "/lisp/cadnorma.dcl")))
  (if (not (new_dialog "cn10_cfg_eixp" dcl_id)) (exit))
  ;estilo do texto
  (setq eixp_text_stylist
	 (list "r50" "r60" "r70" "r80" "r90" "r100" "r120" "r140" "r175" "r200"
			    "t1" "t2" "t3" "t4" "t5" "t6" "t7")
  )
  (start_list "eixp_text_style")
  (mapcar 'add_list eixp_text_stylist)
  (end_list)
  (set_tile "eixp_text_style" eixp_text_sty)
  (action_tile "eixp_text_style" "(setq eixp_text_sty $value)")
  ;cor do texto
  (start_image "eixp_text_color")
  (fill_image  0  0
    (dimx_tile "eixp_text_color")
    (dimy_tile "eixp_text_color")
    (fix (distof eixp_text_col))
  )
  (end_image)
  (action_tile "eixp_text_color" "(eixp_txcol)")
  ;cor do círculo
  (start_image "eixp_circ_color")
  (fill_image  0  0
    (dimx_tile "eixp_circ_color")
    (dimy_tile "eixp_circ_color")
    (fix (distof eixp_circ_col))
  )
  (end_image)
  (action_tile "eixp_circ_color" "(eixp_cccol)")
  ;tipo de linha do eixo
  (setq eixp_eixo_ltlist
	 (list "Center" "Center2" "Phantom" "Phantom2"
	       "Dashdot" "Dashdot2" "Divide" "Divide2" "Continuous")
  )
  (start_list "eixp_eixo_ltype")
  (mapcar 'add_list eixp_eixo_ltlist)
  (end_list)
  (set_tile "eixp_eixo_ltype" eixp_eixo_lty)
  (action_tile "eixp_eixo_ltype" "(setq eixp_eixo_lty $value)")
  ;cor do eixo
  (start_image "eixp_eixo_color")
  (fill_image  0  0
    (dimx_tile "eixp_eixo_color")
    (dimy_tile "eixp_eixo_color")
    (fix (distof eixp_eixo_col))
  )
  (end_image)
  (action_tile "eixp_eixo_color" "(eixp_excol)")
  (action_tile "cancel" "(done_dialog 0)")
  (action_tile "accept" "(done_dialog 1)")
  (setq eixp_format_dcl (start_dialog))
  (unload_dialog dcl_id)
  (if (= 0 eixp_format_dcl) (exit))
  (if (= 1 eixp_format_dcl)
    (progn
      (eixp_write_file)
      (eixp_read_file)
      (eixp_action)
    )
   ) 
)

;escolher a cor do círculo
(defun eixp_cccol ()
  (setq eixp_circ_newcol (acad_colordlg (fix (distof eixp_circ_col))))
  (if (/= nil eixp_circ_newcol) (setq eixp_circ_col (rtos eixp_circ_newcol 2 0)))
  (start_image "eixp_circ_color")
  (fill_image  0  0
    (dimx_tile "eixp_circ_color")
    (dimy_tile "eixp_circ_color")
    (fix (distof eixp_circ_col))
  )
  (end_image)
)

;escolher a cor do círculo
(defun eixp_excol ()
  (setq eixp_eixo_newcol (acad_colordlg (fix (distof eixp_eixo_col))))
  (if (/= nil eixp_eixo_newcol) (setq eixp_eixo_col (rtos eixp_eixo_newcol 2 0)))
  (start_image "eixp_eixo_color")
  (fill_image  0  0
    (dimx_tile "eixp_eixo_color")
    (dimy_tile "eixp_eixo_color")
    (fix (distof eixp_eixo_col))
  )
  (end_image)
)


;escolher a cor do texto
(defun eixp_txcol ()
  (setq eixp_text_newcol (acad_colordlg (fix (distof eixp_text_col))))
  (if (/= nil eixp_text_newcol) (setq eixp_text_col (rtos eixp_text_newcol 2 0)))
  (start_image "eixp_text_color")
  (fill_image  0  0
    (dimx_tile "eixp_text_color")
    (dimy_tile "eixp_text_color")
    (fix (distof eixp_text_col))
  )
  (end_image)
)

;desenha o eixo
(defun eixp_draw ()
  (setq colmo (getvar "cecolor"))
  (setq grp_type "2")
  (cn7_find_blkscl)
  (setq pt2 (getpoint pt1 "\nSegundo Ponto... "))
  (eixp_defradius)
  (cond
    ((= cn7_dwgunit 1) (setq pt3 (polar pt1 (angle pt1 pt2) (* 0.15 cn7_blkscl eixp_cric_rad))))
    ((= cn7_dwgunit 100) (setq pt3 (polar pt1 (angle pt1 pt2) (* 0.15 cn7_blkscl eixp_cric_rad))))
    ((= cn7_dwgunit 1000) (setq pt3 (polar pt1 (angle pt1 pt2) (* 0.15 cn7_blkscl eixp_cric_rad))))
  )
  (cn7_verylayer (strcat cn7_blk_prefixlay "Eixos_projeto") 7)
  (command "._circle" "_non" pt1 "_non" pt3
	   "._chprop" (entlast) "" "_c" (fix (distof eixp_circ_col)) ""
	   "._line" "_non" pt3 "_non" pt2 ""
	   "._chprop" (entlast) "" "_lt" (nth (fix (distof eixp_eixo_lty)) eixp_eixo_ltlist) "_c" (fix (distof eixp_eixo_col)) "")
  (setq psimb_txt pt1)
  (setq eixp_name (getstring "\nNome do Eixo...: "))
  (cn7_txsimb eixp_txstyle "_mc" eixp_name (fix (distof eixp_text_col)) (strcat cn7_blk_prefixlay "Eixos_projeto") 0)
  (command "._chprop" (entlast) "" "_c" (fix (distof eixp_text_col)) "")
)


;define o raio do círculo
(defun eixp_defradius ()
  (cond
    ((= eixp_text_sty "0") (setq eixp_cric_rad hf_r50 eixp_txstyle "r50"))
    ((= eixp_text_sty "1") (setq eixp_cric_rad hf_r60 eixp_txstyle "r60"))
    ((= eixp_text_sty "2") (setq eixp_cric_rad hf_r70 eixp_txstyle "r70"))
    ((= eixp_text_sty "3") (setq eixp_cric_rad hf_r80 eixp_txstyle "r80"))
    ((= eixp_text_sty "4") (setq eixp_cric_rad hf_r90 eixp_txstyle "r90"))
    ((= eixp_text_sty "5") (setq eixp_cric_rad hf_r100 eixp_txstyle "r100"))
    ((= eixp_text_sty "6") (setq eixp_cric_rad hf_r120 eixp_txstyle "r120"))
    ((= eixp_text_sty "7") (setq eixp_cric_rad hf_r140 eixp_txstyle "r140"))
    ((= eixp_text_sty "8") (setq eixp_cric_rad hf_r175 eixp_txstyle "r175"))
    ((= eixp_text_sty "9") (setq eixp_cric_rad hf_r200 eixp_txstyle "r200"))
    ((= eixp_text_sty "10") (setq eixp_cric_rad (distof t1_alt) eixp_txstyle "t1"))
    ((= eixp_text_sty "11") (setq eixp_cric_rad (distof t2_alt) eixp_txstyle "t2"))
    ((= eixp_text_sty "12") (setq eixp_cric_rad (distof t3_alt) eixp_txstyle "t3"))
    ((= eixp_text_sty "13") (setq eixp_cric_rad (distof t4_alt) eixp_txstyle "t4"))
    ((= eixp_text_sty "14") (setq eixp_cric_rad (distof t5_alt) eixp_txstyle "t5"))
    ((= eixp_text_sty "15") (setq eixp_cric_rad (distof t6_alt) eixp_txstyle "t6"))
    ((= eixp_text_sty "16") (setq eixp_cric_rad (distof t7_alt) eixp_txstyle "t7"))
  )
  (setq eixp_rad (* cn7_blkscl eixp_cric_rad))
)

				

;verifica se existe o arquivo de configuração e lê
(defun eixp_file ()
  (if (not (findfile (strcat cnp_root "/config/eixp.txt")))
    (progn
      (setq open_file (open (strcat cnp_root "/config/eixp.txt") "w" "utf8"))
      (write-line "7" open_file)
      (write-line "5" open_file)
      (write-line "8" open_file)
      (write-line "0" open_file)
      (write-line "8" open_file)
      (close open_file)
    )
  )
  (eixp_read_file)
)

;lê os dados do arquivo de configurações
(defun eixp_read_file()
  (setq open_file (open (strcat cnp_root "/config/eixp.txt") "r" "utf8")
	eixp_text_sty (read-line open_file)
	eixp_text_col (read-line open_file)
	eixp_circ_col (read-line open_file)
	eixp_eixo_lty (read-line open_file)
	eixp_eixo_col (read-line open_file)
  )
)

;escreve o arquivo de configurações
(defun eixp_write_file ()
  (setq open_file (open (strcat cnp_root "/config/eixp.txt") "w" "utf8"))
  (write-line eixp_text_sty open_file)
  (write-line eixp_text_col open_file)
  (write-line eixp_circ_col open_file)
  (write-line eixp_eixo_lty open_file)
  (write-line eixp_eixo_col open_file)
  (close open_file)
)  
    

;criação de eixos tipo1
(defun c:ex1 ()
  (guarda '("blipmode" "cecolor" "celtype" "clayer" "cmdecho" "orthomode"
          "textstyle" "luprec" "osmode" ))
  (setq grp_type "2")
  (cn7_find_blkscl)
  (setq pt1 (getpoint "\nPonto de Insercao:"))
  (setq pt2 (getpoint pt1 "\nSegundo Ponto... "))
  (setq pt3 (polar pt1 (angle pt1 pt2) (* cn7_blkscl 0.38)))
  (setq numdes (getstring "\nNumero do Eixo: "))
  (if (not (tblsearch "layer" (strcat cn7_blk_prefixlay "Eixos")))
    (setq eix_color (acad_colordlg 7)))
  (cn7_verylayer (strcat cn7_blk_prefixlay "Eixos") eix_color)
  (setq attdia_mode (getvar "attdia"))
  (setvar "attdia" 0)
  (command "._insert" (strcat cnp_root "/blocos/cvg_ex1") "s" cn7_blkscl "_non" pt1 "0" numdes)
  (setvar "attdia" attdia_mode)
  (command "._line" "_non" pt3 "_non" pt2 "" "._chprop" (entlast) "" "_lt" "center2" "")
  (devolve)
  (princ)
)

;criação de eixos tipo2
(defun c:ex2 (/ om culayer dire ang numdes numprancha pt1 dist dist1)
  (guarda '("blipmode" "cecolor" "celtype" "clayer" "cmdecho" "orthomode"
	    "textstyle" "luprec" "osmode" ))
  (setvar "cmdecho" 0)
  (setq pt1 (getpoint "\nPonto de Insercao:"))
  (setq pt2 (getpoint pt1 "\nSegundo Ponto"))
  (setq angulo (angle pt1 pt2))
  (if (= angulo nil) (setq angulo 0.0))
  (setq ang (rtos (* angulo (/ 180 pi))))
  (if (= ang nil) (setq ang "0"))
  (setq grp_type "2")
  (cn7_find_blkscl)
    (if (not (tblsearch "layer" (strcat cn7_blk_prefixlay "Eixos2")))
    (setq eix_color (acad_colordlg 7)))
  (cn7_verylayer (strcat cn7_blk_prefixlay "Eixos2") eix_color)
  (command "._insert" (strcat cnp_root "/blocos/cvg_ex2") "_scale" cn7_blkscl "_non" pt1 ang)
  (setq pt1 (polar pt1 (angle pt2 pt1) (* cn7_blkscl 0.40)))
  (setvar "orthomode" 1)
  (command "._line" "_non" pt1 "_non" pt2 "")
  (command "._chprop" "_l" "" "_lt" "dashdot2" "")
  (devolve)
  (setq grp_type nil)
  (princ)
)

;criação de eixos tipo3
(defun c:ex3 (/ om culayer dire ang numdes numprancha pt1 dist dist1)
  (guarda '("blipmode" "cecolor" "celtype" "clayer" "cmdecho" "orthomode"
	    "textstyle" "luprec" "osmode" ))
  (setvar "cmdecho" 0)
  (setq pt1 (getpoint "\nPonto de Insercao:"))
  (setq pt2 (getpoint pt1 "\nSegundo Ponto"))
  (setq angulo (angle pt1 pt2))
  (if (and (> angulo 0) (<= angulo pi)) (setq angulo (+ angulo pi)))
  (if (= angulo nil) (setq angulo 0.0))
  (setq ang (rtos (* angulo (/ 180 pi))))
  (if (= ang nil) (setq ang "0"))
  (setq grp_type "2")
  (cn7_find_blkscl)
    (if (not (tblsearch "layer" (strcat cn7_blk_prefixlay "Eixos3")))
    (setq eix_color (acad_colordlg 7)))
  (cn7_verylayer (strcat cn7_blk_prefixlay "Eixos3") eix_color)
  (command "._insert" (strcat cnp_root "/blocos/cvg_ex3") "_scale" cn7_blkscl "_non" pt1 ang)
  (setq pt1 (polar pt1 (angle pt2 pt1) (* cn7_blkscl 0.40)))
  (setvar "orthomode" 1)
  (command "._line" "_non" pt1 "_non" pt2 "")
  (command "._chprop" "_l" "" "_lt" "dashdot2" "")
  (devolve)
  (setq grp_type nil)
  (princ)
)


;desenvolvimento
;escalas gráficas
(defun c:scg ()
  (prompt "\nInserção de Escala Gráfica")
  (if (and (= 0 (getvar "tilemode")) (= 1 (getvar "cvport")))
    (progn
      (cn7_alert_ok
	"Comando permitido apenas no Model"
	"ou em uma Viewport ativa!"
	"Ative uma Viewport ou o Model e reinicie o comando.")
      (quit)
    )
    (progn
      (if (= 1 (getvar "tilemode"))	;se está no Model
	(setq scg_scale cn7_msscl)
	(progn				;se está em uma viewport
	  (cn7_vport_scl)
	  (setq scg_scale cn7_vp_scale)
	)
      )
    )
  )
  (cond
    ((= scg_scale 1.25) (setq scg_blkname  (strcat cnp_root "/blocos/esc_graf_1_25")))
    ((= scg_scale 1.5)  (setq scg_blkname  (strcat cnp_root "/blocos/esc_graf_1_5")))
    ((= scg_scale 2.5)  (setq scg_blkname  (strcat cnp_root "/blocos/esc_graf_2_5")))
    ((= scg_scale 7.5)  (setq scg_blkname  (strcat cnp_root "/blocos/esc_graf_7_5")))
    ((= scg_scale 12.5) (setq scg_blkname  (strcat cnp_root "/blocos/esc_graf_12_5")))
    (t (setq scg_blkname (strcat  (strcat cnp_root "/blocos/esc_graf_" (rtos scg_scale 2 0)))))
  )
  (prompt "\nClique no ponto de inserção... ")
  (if (not (findfile (strcat scg_blkname ".dwg")))
    (progn
      (alert "Escala Gráfica não definida!\nAjuste a escala antes de usar este comando.")
      (quit)
    )
    (command "._insert" scg_blkname "_s" cn7_dwgunit pause 0.0)
  )
  (princ)
)
   

;novo esquema de corte
(defun c:crt1 ()
  (guarda '("blipmode" "cecolor" "celtype" "clayer" "cmdecho" "orthomode"
          "textstyle" "luprec" "osmode" ))
  (setvar "cmdecho" 0)
  (setq pt1 (getpoint "\nPonto do símbolo de corte... ")
	pt2 (getpoint pt1 "\nLinha de corte... ")
	angulo (angle pt1 pt2)
	nome_crt (getstring "\nNome do Corte... ")
	numr_dwg (getstring "\nNúmero do Desenho... ")
  )
  (setq grp_type "2")
  (cn7_find_blkscl)
  (cn7_verylayer (strcat cn7_blk_prefixlay "Cortes") 7)
  (setq attdia_mode (getvar "attdia"))
  (setvar "attdia" 0)
  (command "._insert"  (strcat cnp_root "/blocos/crt1_b2") "_s" cn7_blkscl "_non" pt1 0 nome_crt numr_dwg)
  (setvar "attdia" attdia_mode)
  (setq pt3 (polar pt1 angulo (* cn7_blkscl 0.8485)))
  (command "._line" "_non" pt3 "_non" pt2 "")
  (command "._chprop" "_l" "" "_lt" "dashdot" "_color" "5" "")
  (command "._insert"  (strcat cnp_root "/blocos/crt1_b1") "_s" cn7_blkscl "_non" pt1 "_non" pt2)
  (initget "Sim Nao")
  (setq resp (getkword "\nInverter corte <S/N>? <N> "))
  (if (= resp "Sim") (command "._mirror" (entlast) "" "_non" pt1 "_non" pt2 "_y"))
  (princ)
)

;corte 2
(defun c:crt2 ()
  (guarda '("blipmode" "cecolor" "celtype" "clayer" "cmdecho" "orthomode"
          "textstyle" "luprec" "osmode" ))
  (setvar "cmdecho" 0)
  (setq pt1 (getpoint "\nPonto do símbolo de corte... ")
	pt2 (getpoint pt1 "\nLinha de corte... ")
	angulo (angle pt1 pt2)
	nome_crt (getstring "\nNome do Corte... ")
  )
  (setq grp_type "2")
  (cn7_find_blkscl)
  (cn7_verylayer (strcat cn7_blk_prefixlay "Cortes") 7)
  (setq attdia_mode (getvar "attdia"))
  (setvar "attdia" 0)
  (command "._insert"  (strcat cnp_root "/blocos/crt2_b2") "_s" cn7_blkscl "_non" pt1 0 nome_crt)
  (setvar "attdia" attdia_mode)
  (setq pt3 (polar pt1 angulo (* cn7_blkscl 0.8485)))
  (command "._line" "_non" pt3 "_non" pt2 "")
  (command "._chprop" "_l" "" "_lt" "dashdot" "_color" "5" "")
  (command "._insert"  (strcat cnp_root "/blocos/crt2_b1") "_s" cn7_blkscl "_non" pt1 "_non" pt2)
  (initget "Sim Nao")
  (setq resp (getkword "\nInverter corte <S/N>? <N> "))
  (if (= resp "Sim") (command "._mirror" (entlast) "" "_non" pt1 "_non" pt2 "_y"))
  (princ)
)

;símbologia de níveis
(defun c:nvp ()
  (if (= nil nv_enchimento) (nv_enchim))
  (niv_planta)
  (princ)
)
  
(defun niv_planta (/ culayer cota1 cota2 dist dist1)
  (guarda '("blipmode" "cecolor" "celtype" "clayer" "cmdecho" "orthomode"
          "textstyle" "luprec" "osmode" ))
  (setq dzin_mo (getvar "dimzin"))
  (if (= nil nv_enchimento) (nv_enchim))
  (setvar "cmdecho" 0)
  (initget 128)
  (setq pt1 (getpoint "\nEnchimento/<Ponto de inserção>... "))
  (cond
    ;se clicar num ponto
    ((= 'LIST (type pt1))
     (setq cota1 (getreal "\nNível Acabado: ")
	   cota2 (- cota1 nv_enchimento))
     (setvar "dimzin" 0)
     (cond
       ((>= cota1 0.0) (setq cota1_txt (strcat "+" (rtos cota1 2 2))))
       (t (setq cota1_txt (rtos cota1 2 1)))
     )
     (cond
       ((= cota2 0.0) (setq cota2_txt "0.00"))
       ((>= cota2 0.0) (setq cota2_txt (strcat "+" (rtos cota2 2 2))))
       (t (setq cota2_txt (rtos cota2 2 2)))
     )
     (setq grp_type "2")
     (cn7_find_blkscl)
     (cn7_verylayer (strcat cn7_blk_prefixlay "Níveis") 1)
     (setq attdia_mode (getvar "attdia"))
     (setvar "attdia" 0)
     
     (if (= nv_enchimento 0.0)
       (command "._insert"  (strcat cnp_root "/blocos/cvg_nvp2") "_scale" cn7_blkscl "_non" pt1 "0" cota1_txt "")
       (command "._insert"  (strcat cnp_root "/blocos/cvg_nvp2") "_scale" cn7_blkscl "_non" pt1 "0" cota1_txt cota2_txt)
     )
     (setvar "attdia" attdia_mode)
     (setq dist (rtos (* cn7_blkscl 0.20)))
     (setq dist1 (strcat "@" dist ",0"))
     (prompt "\nDesenhe a linha: ")
     (setvar "orthomode" 1)
     (command "._line" "_non" dist1 pause "")
     (setvar "dimzin" dzin_mo))
    ((= 'STR  (type pt1))
     (cond
       ((= "E" (strcase pt1))
	(nv_enchim)
	(niv_planta)
       )
       (t
	(prompt "\nOpção inválida... Marque o ponto ou digite <E> para enchimento...")
	(niv_planta)
       )
     )
    )
  );cond
  (devolve)
  (setq grp_type nil)
  (princ)
)


;níveis em corte tipo 1
(defun c:nvc1 ()
  (setq nvc_type 1)
  (if (= nil nv_enchimento) (nv_enchim))
  (if (= nil nv_prefix) (setq nv_prefix "Sim"))
  (if (or (= nil nv_pt0) (= nil nv_relativo)) (cvg_nv_def))
  (cvg_nivel)
  (princ)
)

;níveis em corte tipo 2
(defun c:nvc2 ()
  (setq nvc_type 2)
  (if (= nil nv_enchimento) (nv_enchim))
  (if (= nil nv_prefix) (setq nv_prefix "Sim"))
  (if (or (= nil nv_pt0) (= nil nv_relativo)) (cvg_nv_def))
  (cvg_nivel)
  (princ)
)

(defun cvg_nivel ()
  (setq niv_invert (ssadd))
  (setvar "mirrtext" 0)
  (if (= nil nv_enchimento) (nv_enchim))
  (guarda '("blipmode" "cecolor" "celtype" "clayer" "cmdecho" "orthomode"
      "textstyle" "luprec" "osmode" ))
  (initget 128)
  (setq nv_pt1 (getpoint "\nPrefixo/Referência/Enchimento/<Ponto a identificar>..."))
  (setq attdia_mode (getvar "attdia"))
  (setvar "attdia" 0)
  (setvar "orthomode" 1)
  (cond
    ;se clicar num ponto
    ((= 'LIST (type nv_pt1))
     (setq nv_ptinsert (getpoint nv_pt1 "\nPosição do símbolo..."))
     (setq nv_y1_pt1 (nth 1 nv_pt1)
	   y1_pt1 (+ (- nv_y1_pt1 nv_y_pt0) nv_relativo)
	   y2_pt1 (- y1_pt1 nv_enchimento))
     (setq grp_type "2")
     (cn7_find_blkscl)
     (cn7_verylayer (strcat cn7_blk_prefixlay "Níveis") 1)
     (if (= nvc_type 2)
       (command ".insert"  (strcat cnp_root "/blocos/util_st1") "_non" nv_pt1 cn7_blkscl "" "_non" nv_ptinsert)
       (command ".insert"  (strcat cnp_root "/blocos/cvg_nvc2") "_non" nv_pt1 cn7_blkscl "" "_non" nv_ptinsert)
     )
     (setq niv_invert (ssadd (entlast) niv_invert))
     (command "._line" "_non" nv_pt1 "_non" nv_ptinsert "")
     (setq niv_invert (ssadd (entlast) niv_invert))
     ;se é positivo, coloca "+"
     (setq dzin_mo (getvar "dimzin"))
     (setvar "dimzin" 0)
     (if (>= y1_pt1 0)
       (setq txt1 (strcat "+" (rtos y1_pt1 2 2)))
       (setq txt1 (rtos y1_pt1 2 2))
     )
     (if (> y2_pt1 0)
       (setq txt2 (strcat "+" (rtos y2_pt1 2 2)))
       (setq txt2 (rtos y2_pt1 2 2))
     )
     (if (= nv_prefix "Sim") (setq txt1 (strcat "PA:" txt1)
				   txt2 (strcat "PO:" txt2)))    
     (setvar "dimzin" dzin_mo)
     (if (/= 0 nv_enchimento)
       (if (= nvc_type 2)
	 (command "._insert"  (strcat cnp_root "/blocos/cvg_nvp2") "_non" nv_ptinsert cn7_blkscl "" 0 txt1 txt2)
	 (command "._insert"  (strcat cnp_root "/blocos/cvg_nvc2a") "_non" nv_ptinsert cn7_blkscl "" 0 txt1 txt2)
       )
       (if (= nvc_type 2)
	 (command "._insert"  (strcat cnp_root "/blocos/cvg_nvp2") "_non" nv_ptinsert cn7_blkscl "" 0 txt1 "")
	 (command "._insert"  (strcat cnp_root "/blocos/cvg_nvc2a") "_non" nv_ptinsert cn7_blkscl "" 0 txt1 "")
       )
     )
     (setq niv_invert (ssadd (entlast) niv_invert))
     (setvar "mirrtext" 0)
     (setq dist (rtos (* cn7_blkscl 0.20)))
     (setq dist1 (strcat "@" dist ",0"))
     (setvar "orthomode" 1)
     (prompt "\nDesenhe a linha...: ")
     (command "._line" "_non" dist1 "_non" pause "")
     (setq niv_invert (ssadd (entlast) niv_invert))
     (setvar "mirrtext" 0)
     (command "._layer" "_s" culayer "")
     (initget "Sim Não")
     (setq resp (getkword "\nDeseja inverter o símbolo? (S / <N>): "))
     (if (= nil resp) (setq resp "Não"))
     (if (= resp "Sim")
       (command "._mirror" niv_invert "" "_non" nv_pt1 "_non" "@0,1" "y")
     )
     (princ)
    )
    ;se digitar uma letra
    ((= 'STR  (type nv_pt1))
     (cond
       ((= "R" (strcase nv_pt1))
	(cvg_nv_def)
	(cvg_nivel)
       )
       ((= "E" (strcase nv_pt1))
	(nv_enchim)
	(cvg_nivel)
       )
       ((= "P" (strcase nv_pt1))
	(nv_prefixo)
	(cvg_nivel)
       )
       (t
	(prompt "\nOpção inválida... Marque o ponto ou digite <R> para referência...")
	(cvg_nivel)
       )
     )
    )
  )
  (setvar "attdia" attdia_mode)
  (devolve)
)

;define o ponto de referência
(defun cvg_nv_def ()
  (setq nv_pt0 (getpoint "\nSelecione um ponto de referência..."))
  (if (/= nil nv_pt0)
    (progn
      (setq nv_y_pt0 (nth 1 nv_pt0)
	    nv_relativo (getreal "\nNível nesse ponto (piso acabado)... <ENTER=0.0>: "))
      (if (= nil nv_relativo) (setq nv_relativo 0.0))
    )      
  )
)

;definição do enchimento
(defun nv_enchim ()
  (setq nv_enchimento (getreal "\nEspessura do enchimento...<ENTER=0.0>... "))
  (if (= nil nv_enchimento) (setq nv_enchimento 0.0))
)

;defini se coloca ou não o prefixo
(defun nv_prefixo ()
  (initget "Sim Não")
  (setq nv_prefix (getkword "\nAcrescentar prefixos PA e PO <S/N>...(ENTER=Sim)...? "))
  (if (= nil nv_prefix) (setq nv_prefix "Sim"))
  (princ)
)


;função para inserir a inclinação de uma direção
(defun c:incl ()
  (if (= nil incl_dec) (setq incl_dec 1))
  (cvg_incl)
  (princ)
)

(defun cvg_incl ()
  (guarda '("blipmode" "cecolor" "celtype" "clayer" "cmdecho" "orthomode"
      "textstyle" "luprec" "osmode" ))
  (setq attdia_mo (getvar "attdia")
	dzin_mo (getvar "dimzin"))
 (initget 128)
 (setq pt1 (getpoint "\nDecimais/<Primeiro ponto>..."))
  (cond
    ;se clicar num ponto
    ((= 'LIST (type pt1))
     (setq pt2 (getpoint pt1 "\nSegundo ponto...")
	   incl_ang (angle pt1 pt2)
	   pt3 (getpoint "Ponto onde inserir o símbolo...(ENTER=Primeiro ponto)... "))
     (if (= nil pt3) (setq pt3 pt1))
     (if (and (> incl_ang (/ pi 2)) (< incl_ang (/ (* 3 pi) 2)))
       (setq pt4 (polar pt3 (+ pi incl_ang) (distance pt1 pt2)))
       (setq pt4 (polar pt3 incl_ang (distance pt1 pt2)))
     )
     (setq inclina (abs (* 100 (/ (- (nth 1 pt2) (nth 1 pt1)) (- (nth 0 pt2) (nth 0 pt1))))))
     (setvar "dimzin" 0)
     (setq inclina_txt (strcat "i=" (rtos inclina 2 incl_dec) "%"))
     (setvar "dimzin" dzin_mo)
     (setvar "attdia" 0)
     (setq grp_type "2")
     (cn7_find_blkscl)
     (cn7_verylayer (strcat cn7_blk_prefixlay "Inclinações") 1)
     (if (and (> incl_ang (/ pi 2)) (< incl_ang (/ (* 3 pi) 2)))
       (command "._insert"  (strcat cnp_root "/blocos/cvg_incl2") "_non" pt3 cn7_blkscl "" "_non" pt4 inclina_txt)
       (command "._insert"  (strcat cnp_root "/blocos/cvg_incl") "_non" pt3 cn7_blkscl "" "_non" pt4 inclina_txt)
     )
     (setvar "attdia" attdia_mo)
    )
    ((= 'STR  (type pt1))
     (cond       
       ((= "D" (strcase pt1))
	(inclina_dec)
	(cvg_incl)
       )
       (t
	(prompt "\nOpção inválida... Marque o ponto ou digite <R> para referência...")
	(cvg_incl)
       )
     )
   )
  );cond
  (devolve)
)

;define o número de decimais a usar
(defun inclina_dec ()
  (setq incl_dec (getint "\nNúmero de casas decimais...(ENTER=1)... "))
  (if (= nil incl_dec) (setq incl_dec 1))
)


;marcação de declividade
(defun c:decl ()
  (guarda '("blipmode" "cecolor" "celtype" "clayer" "cmdecho" "orthomode"
      "textstyle" "luprec" "osmode" ))
  (prompt "\nSelecione a linha no ponto superior da marcação...")
  (setq osmo (getvar "osmode"))
  (setvar "osmode" 512)
  (setq ent (entsel)
	entmanr (car ent)
	pt1 (nth 1 ent)
	pt2 (getpoint pt1 "\nPonto inferior... "))
  (setq grp_type "2")
  (cn7_find_blkscl)
  (cn7_verylayer (strcat cn7_blk_prefixlay "Inclinações") 1)
  (command "._line" "_nea" pt1 (setq pt3 (getvar "lastpoint")) ".x" "@" pt2 "")
  (setvar "osmode" osmo)
  (setq pt4 (getvar "lastpoint") l2 (entlast))
  (command "._line" "_non" pt2 "_non" pt4 "")
  (setq l1 (entlast))
  (if (or (= pt2 pt3) (= (nth 0 pt2) (nth 0 pt3)) (= (nth 1 pt2) (nth 1 pt3)))
    (progn
      (alert "Inpossível marcar linhas\norizontais ou Verticais!")
      (exit)
     )
  )
  (setq
    dx (- (nth 0 pt4) (nth 0 pt2))
    dy (- (nth 1 pt3) (nth 1 pt4))
    razao (rtos (abs (/ dy dx)) 2 2))
  (if (> (nth 0 pt4) (nth 0 pt2))
    (progn
      (setq pt5 (polar pt2 0 (/ (distance pt2 pt4) 2))
	    psimb_txt (polar pt5 (/ (* 3 pi) 2) (* 0.1 cn7_blkscl)))
      (cn7_txsimb "r60" "tc" "1" 1 "Inclinações" 0)
      (setq txt1 (entlast))
      (setq pt6 (polar pt4 (/ pi 2) (/ (distance pt4 pt3) 2))
	    psimb_txt (polar pt6 0 (* 0.1 cn7_blkscl)))
      (cn7_txsimb "r60" "ml" razao 1 "Inclinações" 0)
      (setq txt2 (entlast))
    )
    (progn
      (setq pt5 (polar pt4 0 (/ (distance pt2 pt4) 2))
	    psimb_txt (polar pt5 (/ (* 3 pi) 2) (* 0.1 cn7_blkscl)))
      (cn7_txsimb "r60" "tc" "1" 1 "Inclinações" 0)
      (setq txt1 (entlast))
      (setq pt6 (polar pt4 (/ pi 2) (/ (distance pt4 pt3) 2))
	    psimb_txt (polar pt6 pi (* 0.1 cn7_blkscl)))
      (cn7_txsimb "r60" "mr" razao 1 "Inclinações" 0)
      (setq txt2 (entlast))
    )
  )
  (initget "Sim Não")
  (setq resp (getkword "\nColocar a simbologia acima da linha <S/N>?...(ENTER=Não)... "))
  (if (= resp nil) (setq resp "Não"))
  (if (= resp "Sim")
    (progn
      (command "._mirror" l1 txt1 "" pt6 "_non" "@1,0" "_y")
      (command "._mirror" l2 txt2 "" pt5 "_non" "@0,1" "_y")
    )
  )
  (devolve)
  (princ)
)



;***********************************************
;Legendas
;***********************************************
(defun c:leg ()
  (setq leg_ins nil)
  (setq dcl_id (load_dialog (strcat cnp_root "/lisp/cadnorma.dcl")))
  (if (not (new_dialog "leg" dcl_id)) (exit))

  ;preenche a lista de funções
  (start_list "cvg_list")
  (mapcar 'add_list
	  (list  "<ID1>" "<ID2>" "<ID3>" "<ID4>" "<ID5>"
		 "<ID6>" "<ID7>" "<ID8>" "<ID9>" "<ID10>"
		 "<ID11>" "<ID12>" "<ID13>" "<ID14>" "<ID15>"
		 "<ID16>" "<ID17>" "<ID18>" "<ID19>" "<ID20>"))
  (end_list)
  (action_tile "cvg_list" "(setq leg_ins (read $value))")
  (action_tile "icon11" "(leg_icon 0)")
  (action_tile "icon12" "(leg_icon 1)")
  (action_tile "icon13" "(leg_icon 2)")
  (action_tile "icon14" "(leg_icon 3)")
  (action_tile "icon21" "(leg_icon 4)")
  (action_tile "icon22" "(leg_icon 5)")
  (action_tile "icon23" "(leg_icon 6)")
  (action_tile "icon24" "(leg_icon 7)")
  (action_tile "icon31" "(leg_icon 8)")
  (action_tile "icon32" "(leg_icon 9)")
  (action_tile "icon33" "(leg_icon 10)")
  (action_tile "icon34" "(leg_icon 11)")
  (action_tile "icon41" "(leg_icon 12)")
  (action_tile "icon42" "(leg_icon 13)")
  (action_tile "icon43" "(leg_icon 14)")
  (action_tile "icon44" "(leg_icon 15)")
  (action_tile "icon51" "(leg_icon 16)")
  (action_tile "icon52" "(leg_icon 17)")
  (action_tile "icon53" "(leg_icon 18)")
  (action_tile "icon54" "(leg_icon 19)")
  (leg_slides);preenche os slides
  (action_tile "accept" "(done_dialog 1)")
  (action_tile "cancel" "(done_dialog 0)")
  (setq cvg_dialog (start_dialog))
  (unload_dialog dcl_id)
  (if (= 1 cvg_dialog) (leg_ok))
  (princ)
)

(defun leg_icon (ic)
  (setq leg_ins ic)
  (set_tile "cvg_list" (rtos ic 2 0))
)

(defun leg_ok ()
  (cond
    ((= leg_ins 0) (leg_aux "cvg_id1"))
    ((= leg_ins 1) (leg_aux "cvg_id2"))
    ((= leg_ins 2) (leg_aux "cvg_id3"))
    ((= leg_ins 3) (leg_aux "cvg_id4"))
    ((= leg_ins 4) (leg_aux "cvg_id5"))
    ((= leg_ins 5) (leg_aux "cvg_id6"))
    ((= leg_ins 6) (leg_aux "cvg_id7"))
    ((= leg_ins 7) (leg_aux "cvg_id8"))
    ((= leg_ins 8) (leg_aux "cvg_id9"))
    ((= leg_ins 9) (leg_aux "cvg_id10"))
    ((= leg_ins 10) (leg_aux "cvg_id11"))
    ((= leg_ins 11) (leg_aux "cvg_id12"))
    ((= leg_ins 12) (leg_aux "cvg_id13"))
    ((= leg_ins 13) (leg_aux "cvg_id14"))
    ((= leg_ins 14) (leg_id15))
    ((= leg_ins 15) (leg_id16))
    ((= leg_ins 16) (leg_aux "cvg_id17"))
    ((= leg_ins 17) (leg_aux "cvg_id18"))
    ((= leg_ins 18) (leg_aux "cvg_id19"))
    ((= leg_ins 19) (leg_aux "cvg_id20"))
  )
)

(defun leg_aux (blk)
  (setq grp_type "2")
  (cn7_find_blkscl)
  (cn7_verylayer (strcat cn7_blk_prefixlay "Legendas") 1)
  (if (not (findfile (strcat cnp_root "/blocos/" blk ".dwg")))
    (progn
      (alert "Bloco não encontrado!")
      (exit)
    )
    (progn
      (setq p1 (getpoint "\nPonto de inserção... "))
      (command "._insert" (strcat cnp_root "/blocos/" blk) "_s" cn7_blkscl p1 0)
    )
  )
)

;legendas
(defun c:id1 () (leg_aux "cvg_id1")(princ))
(defun c:id2 () (leg_aux "cvg_id2")(princ))
(defun c:id3 () (leg_aux "cvg_id3")(princ))
(defun c:id4 () (leg_aux "cvg_id4")(princ))
(defun c:id5 () (leg_aux "cvg_id5")(princ))
(defun c:id6 () (leg_aux "cvg_id6")(princ))
(defun c:id7 () (leg_aux "cvg_id7")(princ))
(defun c:id8 () (leg_aux "cvg_id8")(princ))
(defun c:id9 () (leg_aux "cvg_id9")(princ))
(defun c:id10 () (leg_aux "cvg_id10")(princ))
(defun c:id11 () (leg_aux "cvg_id11")(princ))
(defun c:id12 () (leg_aux "cvg_id12")(princ))
(defun c:id13 () (leg_aux "cvg_id13")(princ))
(defun c:id14 () (leg_aux "cvg_id14")(princ))
(defun c:id17 () (leg_aux "cvg_id17")(princ))
(defun c:id18 () (leg_aux "cvg_id18")(princ))
(defun c:id19 () (leg_aux "cvg_id19")(princ))
(defun c:id20 () (leg_aux "cvg_id20")(princ))

;legendas especiais
(defun c:id15 () (leg_id15)(princ))

(defun leg_id15 ()
  (setq grp_type "2")
  (cn7_find_blkscl)
  (cn7_verylayer (strcat cn7_blk_prefixlay "Legendas") 1)
  (setq pt1 (getpoint "\nPoto de inserção... ")
	pt2 (getpoint pt1 "\nDireção...")
	pt3 (polar pt1 (angle pt1 pt2) (* 0.4 cn7_blkscl))
	pt4 (polar pt1 (angle pt1 pt2) (* 0.8 cn7_blkscl))
	pt5 (polar pt1 (angle pt1 pt2) (* 1.2 cn7_blkscl))
	ang (angle pt1 pt2))
  (cond
    ((or (= ang 0) (= ang (/ pi 2)) (= ang pi) (= ang (* 3 (/ pi 2)))) (setq txang 0))
    ((and (> ang 0) (< ang pi)) (setq txang (/ (* 180 (- ang (/ pi 2))) pi)))
    ((and (> ang pi) (< ang (* 2 pi))) (setq txang (/ (* 180 (+ ang (/ pi 2))) pi)))
  )
  (setq txt1 (getstring "\nA: ")
	txt2 (getstring "\nB: ")
	txt3 (getstring "\nC: "))
  
  (if (not (findfile  (strcat cnp_root "/blocos/cvg_id15.dwg")))
    (progn
      (alert "Bloco não encontrado!")
      (exit)
    )
    (progn
      (command "._insert"  (strcat cnp_root "/blocos/cvg_id15") "_s" cn7_blkscl "_non" pt1 "_non" pt2 txt1 txt2 txt3)
      (setq ent1 (entlast))
      (while (/= "SEQEND" (cdr (assoc 0 (setq selent (entget (setq ent1 (entnext ent1)))))))
	(if (= "ATTRIB" (cdr (assoc 0 selent)))
	  (progn
	    (setq selent_name (cdr (assoc -1 selent)))
	    (command "._attedit" "_y" "" "" "" selent_name "_a" txang "")
	  )
	)
      )
    )
  )
)

(defun c:id16 () (leg_id16)(princ))

(defun leg_id16 ()	  
  (setq grp_type "2")
  (cn7_find_blkscl)
  (cn7_verylayer (strcat cn7_blk_prefixlay "Legendas") 1)
  (setq pt1 (getpoint "\nPonto de inserção... ")
	pt2 (getpoint pt1 "\nDireção...")
	pt3 (polar pt1 (angle pt1 pt2) (* 0.55 cn7_blkscl))
	pt4 (polar pt1 (angle pt1 pt2) (* 0.95 cn7_blkscl))
	ang (angle pt1 pt2))
  (cond
    ((or (= ang 0) (= ang (/ pi 2)) (= ang pi) (= ang (* 3 (/ pi 2)))) (setq txang 0))
    ((and (> ang 0) (< ang pi)) (setq txang (/ (* 180 (- ang (/ pi 2))) pi)))
    ((and (> ang pi) (< ang (* 2 pi))) (setq txang (/ (* 180 (+ ang (/ pi 2))) pi)))
  )
  (setq txt1 (getstring "\nA: ")
	txt2 (getstring "\nB: "))
  
  (if (not (findfile  (strcat cnp_root "/blocos/cvg_id16.dwg")))
    (progn
      (alert "Bloco não encontrado!")
      (exit)
    )
    (progn
      (command "._insert"  (strcat cnp_root "/blocos/cvg_id16") "_s" cn7_blkscl "_non" pt1 "_non" pt2 txt1 txt2)
      (setq ent1 (entlast))
      (while (/= "SEQEND" (cdr (assoc 0 (setq selent (entget (setq ent1 (entnext ent1)))))))
	(if (= "ATTRIB" (cdr (assoc 0 selent)))
	  (progn
	    (setq selent_name (cdr (assoc -1 selent)))
	    (command "._attedit" "_y" "" "" "" selent_name "_a" txang "")
	  )
	)
      )
    )
  )
)

(defun leg_slides ()
  (setq x (dimx_tile "icon11")
	y (dimy_tile "icon11"))
  (start_image "icon11")
  (slide_image 0 0 x y  (strcat cnp_root "/slides/cvg_id1.sld"))
  (end_image)
  (setq x (dimx_tile "icon12")
	y (dimy_tile "icon12"))
  (start_image "icon12")
  (slide_image 0 0 x y  (strcat cnp_root "/slides/cvg_id2.sld"))
  (end_image)
  (setq x (dimx_tile "icon13")
	y (dimy_tile "icon13"))
  (start_image "icon13")
  (slide_image 0 0 x y  (strcat cnp_root "/slides/cvg_id3.sld"))
  (end_image)
  (setq x (dimx_tile "icon14")
	y (dimy_tile "icon14"))
  (start_image "icon14")
  (slide_image 0 0 x y  (strcat cnp_root "/slides/cvg_id4.sld"))
  (end_image)
  ;
  (setq x (dimx_tile "icon21")
	y (dimy_tile "icon21"))
  (start_image "icon21")
  (slide_image 0 0 x y  (strcat cnp_root "/slides/cvg_id5.sld"))
  (end_image)
  (setq x (dimx_tile "icon22")
	y (dimy_tile "icon22"))
  (start_image "icon22")
  (slide_image 0 0 x y  (strcat cnp_root "/slides/cvg_id6.sld"))
  (end_image)
  (setq x (dimx_tile "icon23")
	y (dimy_tile "icon23"))
  (start_image "icon23")
  (slide_image 0 0 x y  (strcat cnp_root "/slides/cvg_id7.sld"))
  (end_image)
  (setq x (dimx_tile "icon24")
	y (dimy_tile "icon24"))
  (start_image "icon24")
  (slide_image 0 0 x y  (strcat cnp_root "/slides/cvg_id8.sld"))
  (end_image)

  ;
  (setq x (dimx_tile "icon31")
	y (dimy_tile "icon31"))
  (start_image "icon31")
  (slide_image 0 0 x y  (strcat cnp_root "/slides/cvg_id9.sld"))
  (end_image)
  (setq x (dimx_tile "icon32")
	y (dimy_tile "icon32"))
  (start_image "icon32")
  (slide_image 0 0 x y  (strcat cnp_root "/slides/cvg_id10.sld"))
  (end_image)
  (setq x (dimx_tile "icon33")
	y (dimy_tile "icon33"))
  (start_image "icon33")
  (slide_image 0 0 x y  (strcat cnp_root "/slides/cvg_id11.sld"))
  (end_image)
  (setq x (dimx_tile "icon34")
	y (dimy_tile "icon34"))
  (start_image "icon34")
  (slide_image 0 0 x y  (strcat cnp_root "/slides/cvg_id12.sld"))
  (end_image)
  (setq x (dimx_tile "icon41")
	y (dimy_tile "icon41"))
  (start_image "icon41")
  (slide_image 0 0 x y  (strcat cnp_root "/slides/cvg_id13.sld"))
  (end_image)
  (setq x (dimx_tile "icon42")
	y (dimy_tile "icon42"))
  (start_image "icon42")
  (slide_image 0 0 x y (strcat cnp_root "/slides/cvg_id14.sld"))
  (end_image)
  (setq x (dimx_tile "icon43")
	y (dimy_tile "icon43"))
  (start_image "icon43")
  (slide_image 0 0 x y (strcat cnp_root "/slides/cvg_id15.sld"))
  (end_image)
  (setq x (dimx_tile "icon44")
	y (dimy_tile "icon44"))
  (start_image "icon44")
  (slide_image 0 0 x y (strcat cnp_root "/slides/cvg_id16.sld"))
  (end_image)
  (setq x (dimx_tile "icon51")
	y (dimy_tile "icon51"))
  (start_image "icon51")
  (slide_image 0 0 x y (strcat cnp_root "/slides/cvg_id17.sld"))
  (end_image)
  (setq x (dimx_tile "icon52")
	y (dimy_tile "icon52"))
  (start_image "icon52")
  (slide_image 0 0 x y (strcat cnp_root "/slides/cvg_id18.sld"))
  (end_image)
  (setq x (dimx_tile "icon53")
	y (dimy_tile "icon53"))
  (start_image "icon53")
  (slide_image 0 0 x y (strcat cnp_root "/slides/cvg_id19.sld"))
  (end_image)
  (setq x (dimx_tile "icon54")
	y (dimy_tile "icon54"))
  (start_image "icon54")
  (slide_image 0 0 x y (strcat cnp_root "/slides/cvg_id20.sld"))
  (end_image)

)


;***********************************************
;Títulos
;***********************************************
(defun c:tit ()
  (setq tit_ins nil)
  (setq dcl_id (load_dialog (strcat cnp_root "/lisp/cadnorma.dcl")))
  (if (not (new_dialog "leg" dcl_id)) (exit))

  ;preenche a lista de funções
  (start_list "cvg_list")
  (mapcar 'add_list
	  (list  "<TT1>" "<TT2>" "<TT3>" "<TT4>" "<TT5>"
		 "<TT6>" "<TT7>" "<TT8>" "<TT9>" "<TT10>"
		 "<TT11>" "<TT12>" "<TT13>" "<TT14>" "<TT15>"
		 "<TT16>" "<TT17>" "<TT18>" "<TT19>" "<TT20>"))
  (end_list)
  (action_tile "cvg_list" "(setq tit_ins (read $value))")
  (action_tile "icon11" "(tit_icon 0)")
  (action_tile "icon12" "(tit_icon 1)")
  (action_tile "icon13" "(tit_icon 2)")
  (action_tile "icon14" "(tit_icon 3)")
  (action_tile "icon21" "(tit_icon 4)")
  (action_tile "icon22" "(tit_icon 5)")
  (action_tile "icon23" "(tit_icon 6)")
  (action_tile "icon24" "(tit_icon 7)")
  (action_tile "icon31" "(tit_icon 8)")
  (action_tile "icon32" "(tit_icon 9)")
  (action_tile "icon33" "(tit_icon 10)")
  (action_tile "icon34" "(tit_icon 11)")
  (action_tile "icon41" "(tit_icon 12)")
  (action_tile "icon42" "(tit_icon 13)")
  (action_tile "icon43" "(tit_icon 14)")
  (action_tile "icon44" "(tit_icon 15)")
  (action_tile "icon51" "(tit_icon 16)")
  (action_tile "icon52" "(tit_icon 17)")
  (action_tile "icon53" "(tit_icon 18)")
  (action_tile "icon54" "(tit_icon 19)")
  (tit_slides)
  (action_tile "accept" "(done_dialog 1)")
  (action_tile "cancel" "(done_dialog 0)")
  (setq cvg_dialog (start_dialog))
  (unload_dialog dcl_id)
  (if (= 1 cvg_dialog) (tit_ok))
  (princ)
)


(defun tit_ok ()
  (cond
    ((= tit_ins 0) (tit_aux "cvg_tt1"))
    ((= tit_ins 1) (tit_aux "cvg_tt2"))
    ((= tit_ins 2) (tit_aux "cvg_tt3"))
    ((= tit_ins 3) (tit_aux "cvg_tt4"))
    ((= tit_ins 4) (tit_aux "cvg_tt5"))
    ((= tit_ins 5) (tit_aux "cvg_tt6"))
    ((= tit_ins 6) (tit_aux "cvg_tt7"))
    ((= tit_ins 7) (tit_aux "cvg_tt8"))
    ((= tit_ins 8) (tit_aux "cvg_tt9"))
    ((= tit_ins 9) (tit_aux "cvg_tt10"))
    ((= tit_ins 10) (tit_aux "cvg_tt11"))
    ((= tit_ins 11) (tit_aux "cvg_tt12"))
    ((= tit_ins 12) (tit_aux "cvg_tt13"))
    ((= tit_ins 13) (tit_aux "cvg_tt14"))
    ((= tit_ins 14) (tit_aux "cvg_tt15"))
    ((= tit_ins 15) (tit_aux "cvg_tt16"))
    ((= tit_ins 16) (tit_aux "cvg_tt17"))
    ((= tit_ins 17) (tit_aux "cvg_tt18"))
    ((= tit_ins 18) (tit_aux "cvg_tt19"))
    ((= tit_ins 19) (tit_aux "cvg_tt20"))
  )
)


(defun tit_icon (ic)
  (setq tit_ins ic)
  (set_tile "cvg_list" (rtos ic 2 0))
)


(defun tit_aux (blk)
  (setq grp_type "2")
  (cn7_find_blkscl)
  (cn7_verylayer (strcat cn7_blk_prefixlay "Títulos") 2)
  (if (not (findfile (strcat cnp_root "/blocos/" blk ".dwg")))
    (progn
      (alert (strcat "Bloco não encontrado!\n" blk))
      (exit)
    )
    (progn
      (setq pt1 (getpoint "\nPonto de Iserção... "))
      (command "._insert" (strcat cnp_root "/blocos/" blk) "_s" cn7_blkscl "_non" pt1)
    )
  )
)

(defun c:tt1 () (tit_aux "cvg_tt1")(princ))
(defun c:tt2 () (tit_aux "cvg_tt2")(princ))
(defun c:tt3 () (tit_aux "cvg_tt3")(princ))
(defun c:tt4 () (tit_aux "cvg_tt4")(princ))
(defun c:tt5 () (tit_aux "cvg_tt5")(princ))
(defun c:tt6 () (tit_aux "cvg_tt6")(princ))
(defun c:tt7 () (tit_aux "cvg_tt7")(princ))
(defun c:tt8 () (tit_aux "cvg_tt8")(princ))
(defun c:tt9 () (tit_aux "cvg_tt9")(princ))
(defun c:tt10 () (tit_aux "cvg_tt10")(princ))
(defun c:tt11 () (tit_aux "cvg_tt11")(princ))
(defun c:tt12 () (tit_aux "cvg_tt12")(princ))
(defun c:tt13 () (tit_aux "cvg_tt13")(princ))
(defun c:tt14 () (tit_aux "cvg_tt14")(princ))
(defun c:tt15 () (tit_aux "cvg_tt15")(princ))
(defun c:tt16 () (tit_aux "cvg_tt16")(princ))
(defun c:tt17 () (tit_aux "cvg_tt17")(princ))
(defun c:tt18 () (tit_aux "cvg_tt18")(princ))
(defun c:tt19 () (tit_aux "cvg_tt19")(princ))
(defun c:tt20 () (tit_aux "cvg_tt20")(princ))


(defun tit_slides ()
  (setq x (dimx_tile "icon11")
	y (dimy_tile "icon11"))
  (start_image "icon11")
  (slide_image 0 0 x y (strcat cnp_root "/slides/cvg_tt1.sld"))
  (end_image)
  (setq x (dimx_tile "icon12")
	y (dimy_tile "icon12"))
  (start_image "icon12")
  (slide_image 0 0 x y (strcat cnp_root "/slides/cvg_tt2.sld"))
  (end_image)
  (setq x (dimx_tile "icon13")
	y (dimy_tile "icon13"))
  (start_image "icon13")
  (slide_image 0 0 x y (strcat cnp_root "/slides/cvg_tt3.sld"))
  (end_image)
  (setq x (dimx_tile "icon14")
	y (dimy_tile "icon14"))
  (start_image "icon14")
  (slide_image 0 0 x y (strcat cnp_root "/slides/cvg_tt4.sld"))
  (end_image)
  (setq x (dimx_tile "icon21")
	y (dimy_tile "icon21"))
  (start_image "icon21")
  (slide_image 0 0 x y (strcat cnp_root "/slides/cvg_tt5.sld"))
  (end_image)
  (setq x (dimx_tile "icon22")
	y (dimy_tile "icon22"))
  (start_image "icon22")
  (slide_image 0 0 x y (strcat cnp_root "/slides/cvg_tt6.sld"))
  (end_image)
  (setq x (dimx_tile "icon23")
	y (dimy_tile "icon23"))
  (start_image "icon23")
  (slide_image 0 0 x y (strcat cnp_root "/slides/cvg_tt7.sld"))
  (end_image)
  (setq x (dimx_tile "icon24")
	y (dimy_tile "icon24"))
  (start_image "icon24")
  (slide_image 0 0 x y (strcat cnp_root "/slides/cvg_tt8.sld"))
  (end_image)
  (setq x (dimx_tile "icon31")
	y (dimy_tile "icon31"))
  (start_image "icon31")
  (slide_image 0 0 x y (strcat cnp_root "/slides/cvg_tt9.sld"))
  (end_image)
  (setq x (dimx_tile "icon32")
	y (dimy_tile "icon32"))
  (start_image "icon32")
  (slide_image 0 0 x y (strcat cnp_root "/slides/cvg_tt10.sld"))
  (end_image)
  (setq x (dimx_tile "icon33")
	y (dimy_tile "icon33"))
  (start_image "icon33")
  (slide_image 0 0 x y (strcat cnp_root "/slides/cvg_tt11.sld"))
  (end_image)
  (setq x (dimx_tile "icon34")
	y (dimy_tile "icon34"))
  (start_image "icon34")
  (slide_image 0 0 x y (strcat cnp_root "/slides/cvg_tt12.sld"))
  (end_image)
  (setq x (dimx_tile "icon41")
	y (dimy_tile "icon41"))
  (start_image "icon41")
  (slide_image 0 0 x y (strcat cnp_root "/slides/cvg_tt13.sld"))
  (end_image)
  (setq x (dimx_tile "icon42")
	y (dimy_tile "icon42"))
  (start_image "icon42")
  (slide_image 0 0 x y (strcat cnp_root "/slides/cvg_tt14.sld"))
  (end_image)
  (setq x (dimx_tile "icon43")
	y (dimy_tile "icon43"))
  (start_image "icon43")
  (slide_image 0 0 x y (strcat cnp_root "/slides/cvg_tt15.sld"))
  (end_image)
  (setq x (dimx_tile "icon44")
	y (dimy_tile "icon44"))
  (start_image "icon44")
  (slide_image 0 0 x y (strcat cnp_root "/slides/cvg_tt16.sld"))
  (end_image)
  (setq x (dimx_tile "icon51")
	y (dimy_tile "icon51"))
  (start_image "icon51")
  (slide_image 0 0 x y (strcat cnp_root "/slides/cvg_tt17.sld"))
  (end_image)
  (setq x (dimx_tile "icon52")
	y (dimy_tile "icon52"))
  (start_image "icon52")
  (slide_image 0 0 x y (strcat cnp_root "/slides/cvg_tt18.sld"))
  (end_image)
  (setq x (dimx_tile "icon53")
	y (dimy_tile "icon53"))
  (start_image "icon53")
  (slide_image 0 0 x y (strcat cnp_root "/slides/cvg_tt19.sld"))
  (end_image)
  (setq x (dimx_tile "icon54")
	y (dimy_tile "icon54"))
  (start_image "icon54")
  (slide_image 0 0 x y (strcat cnp_root "/slides/cvg_tt20.sld"))
  (end_image)

)

;cnp_13


;*************************************************************************************************
;*************************************************************************************************
;Áreas
;*************************************************************************************************
;*************************************************************************************************
(defun c:pka () (pka_action)(princ))

;calcula a área e dá prosseguimento...
(defun pka_action ()
  (guarda '("blipmode" "cecolor" "celtype" "clayer" "cmdecho" "orthomode"
      "textstyle" "luprec" "osmode" ))
  (setq osmo (getvar "osmode"))
  (setq colmo (getvar "cecolor"))
  (initget 128)
  (setq pt1 (getpoint "\nSelecione polyline/Marcar pontos/<Clique em um ponto interno>..."))
  (cond
    ;se clicar num ponto
    ((= 'LIST (type pt1))
     (setvar "cecolor" "214")
     (command "._boundary" "_non" pt1 ""  "._area" "_e" (entlast))
     (setvar "cecolor" colmo)
     (initget "Sim Não")
     (setq resp (getkword (strcat "\nÁrea=<" (rtos (getvar "area") 2 2) ">...Confirma área selecionada? <S/N>...(ENTER=Sim)... ")))
     (if (or (= resp "Sim") (= resp nil))
       (progn
	 (command "._erase" (entlast) "")
	 (area_text)
       )
       (progn
	 (command "._erase" (entlast) "")
	 (devolve)
	 (pka_action)
       )
     );if
    )
    ;se digitar uma letra
    ((= 'STR  (type pt1))
     (cond       
       ((= "S" (strcase pt1))
        (prompt "\nSelecione a Polyline a ser medida...")
	(setq ent1 (entsel))
	(if ent1 (setq ent1_name (car ent1)))
	(command "_area" "_e" ent1_name)
	(princ (strcat "\nÁrea=<" (rtos (getvar "area") 2 2) ">"))
	(area_text)
       )
       ((= "M" (strcase pt1))
	(setq pt1 (getpoint "\nPrimeiro ponto... ")
	      pt2 (getpoint "\nSegundo ponto... ")
	      pt3 (getpoint "\nTerceiro ponto... ")
	)
	(setq pt_list (list pt1 pt2 pt3))
	(while (/= nil (setq pt_next (getpoint "\nPróximo ponto... ")))
	  (setq pt_list (append pt_list (list pt_next)))
	)
	(command "._area")
	(foreach n pt_list
	  (command n)
	)
	(command "")
	(princ (strcat "\nÁrea=<" (rtos (getvar "area") 2 2) ">"))
	(area_text)
       )
       (t
	(prompt "\nOpção inválida... Marque o ponto ou digite <S> para selecionar...")
	(pka_action)
       )
     )
   )
  );cond
  (devolve)
)

;função que decide sobre o texto
(defun area_text ()
  (cn7_cfg_txarea_file)
  (initget 128)
  (setq pt1 (getpoint "\nEditar existente/Formatar texto/<Ponto do texto>..."))
  (cond
    ;se clicar num ponto
    ((= 'LIST (type pt1))
     (area_find_text)
     (area_writext)
    )
    ((= 'STR  (type pt1))
     (cond       
       ((= "E" (strcase pt1))
	(prompt "\nSelecione o texto a ser editado... ")
	(setq s2 (entsel))
	(area_find_text)
	(entmod (subst (cons 1 area_txt) (assoc 1 (entget (car s2))) (entget (car s2))))
       )
       ((= "F" (strcase pt1))
	(cn7_cfgmain_txarea)
	(area_text)
       )
       (t
	(prompt "\nOpção inválida... ")
	(devolve)
	(pka_action)
       )
     )
    )
    (t (exit))
  );cond
)

;encontra o texto exato
(defun area_find_text ()
  ;decimais
  (setq area_dec (fix (distof txarea_dec)))
  ;valor
  (setq area_num (getvar "area"))
  (cond
    ;se a unidade de desenho é metos
    ((= cn7_dwgunit 1.0)
     (cond
       ((= txarea_und "0") (setq area_value (* area_num 1e6) area_sufix "mm2"))
       ((= txarea_und "1") (setq area_value (* area_num 1e4) area_sufix "cm2"))
       ((= txarea_und "2") (setq area_value (* area_num 1.0) area_sufix "m2"))
       ((= txarea_und "3") (setq area_value (/ area_num 1e6) area_sufix "km2"))
     )
    )
    ;se a unidade de desenho é centímetos
    ((= cn7_dwgunit 100.0)
     (cond
       ((= txarea_und "0") (setq area_value (* area_num 1e2) area_sufix "mm2"))
       ((= txarea_und "1") (setq area_value (* area_num 1.0) area_sufix "cm2"))
       ((= txarea_und "2") (setq area_value (/ area_num 1e4) area_sufix "m2"))
       ((= txarea_und "3") (setq area_value (/ area_num 1e10) area_sufix "km2"))
     )
    )
    ;se a unidade de desenho é milímetos
    ((= cn7_dwgunit 1000.0)
     (cond
       ((= txarea_und "0") (setq area_value (* area_num 1.0) area_sufix "mm2"))
       ((= txarea_und "1") (setq area_value (/ area_num 1e2) area_sufix "cm2"))
       ((= txarea_und "2") (setq area_value (/ area_num 1e6) area_sufix "m2"))
       ((= txarea_und "3") (setq area_value (/ area_num 1e12) area_sufix "km2"))
     )
    )
  );cond
  ;texto final
  (if (= txarea_wrt "0")
    (setq area_txt (rtos area_value 2 area_dec))
    (if (= txarea_spc "0")
      (setq area_txt (strcat (rtos area_value 2 area_dec) area_sufix))
      (setq area_txt (strcat (rtos area_value 2 area_dec) " " area_sufix))
    )
  )
)

;escreve, efetivamente, o texto
(defun area_writext ()
  ;ponto de inserção
  (setq psimb_txt pt1)
  ;estilo
  (setq txarea_stylist (list "r50" "r60" "r70" "r80" "r90" "r100" "r120" "r140" "r175" "r200"
			    "t1" "t2" "t3" "t4" "t5" "t6" "t7"))
  (setq area_sty (nth (fix (distof txarea_sty)) txarea_stylist))
  (setq area_angulo (getangle pt1 "\nÂngulo do texto...(ENTER = 0)... "))
  (if (= nil area_angulo)
    (progn
      (setq area_angulo 0.0)
      (setq area_ang 0.0)
    )
    (setq area_ang (/ (* 180.0 area_angulo) pi))
  )
  (cn7_txsimb area_sty "c" area_txt (fix (distof txarea_col)) "Áreas" area_ang)
  (initget "Sim Não")
  (setq resp (getkword "\nAcrescentar nome do Ambiente? <S>/N: "))
  (if (or (= resp nil) (= resp "Sim")) (area_write_place))
)

;escreve o nomedo cômodo
(defun area_write_place ()
  (setq psimb_txt (polar psimb_txt (+ area_angulo (/ pi 2)) (* 1.7 cn7_txth)))
  (setq amb_sty (nth (fix (distof txamb_sty)) txarea_stylist))
  (setq dcl_id (load_dialog (strcat cnp_root "/lisp/cadnorma.dcl")))
  (if (not (new_dialog "cn9_getplace" dcl_id)) (exit))
  (if getplace (set_tile "area_getplace" getplace))
  (mode_tile "area_getplace" 2)
  (action_tile "area_getplace" "(setq getplace $value)")
  (setq cn_txarea_getplace (start_dialog))
  (unload_dialog dcl_id)
  (cn7_txsimb amb_sty "c" getplace (fix (distof txamb_col)) "Ambientes_nomes" area_ang)
)

;***********************************************
;formatação do texto para áreas
;***********************************************
(defun c:txarea () (cn7_cfgmain_txarea)(princ))

;distribuidor
(defun cn7_cfgmain_txarea ()
  (cn7_cfg_txarea_file)
  (cn7_cfg_txarea)
  (if (= cn7_cfgmain_return 1) (cn7_cfg_main))
)

;lê os dados iniciais da DCL no arquivo de dados
(defun cn7_cfg_txarea_file ()
  (if (findfile (strcat cnp_root "/config/txarea.txt"))
    (cn7_txarea_readfile)
    (progn
      (setq file (open (strcat cnp_root "/config/txarea.txt") "w" "utf8"))
      (write-line "3" file)
      (write-line "2" file)
      (write-line "2" file)
      (write-line "1" file)
      (write-line "2" file)
      (write-line "0" file)
      (write-line "4" file)
      (write-line "3" file)
      (close file)
      (cn7_txarea_readfile)
    )
  )
)

;função que lê o arquivo de dados
(defun cn7_txarea_readfile ()
  (setq	file (open (strcat cnp_root "/config/txarea.txt") "r" "utf8"))
  (setq	txarea_sty (read-line file))
  (setq	txarea_dec (read-line file))
  (setq	txarea_und (read-line file))
  (setq	txarea_wrt (read-line file))
  (setq	txarea_col (read-line file))
  (setq	txarea_spc (read-line file))
  (setq	txamb_sty (read-line file))
  (setq	txamb_col (read-line file))
  (close file)
)

(defun cn7_cfg_txarea ()
;abre a dcl
  (setq dcl_id (load_dialog (strcat cnp_root "/lisp/cadnorma.dcl")))
  (if (not (new_dialog "cn7_cfg_txarea" dcl_id)) (exit))
  ;estilo
  (setq txarea_stylist (list "r50" "r60" "r70" "r80" "r90" "r100" "r120" "r140" "r175" "r200"
			    "t1" "t2" "t3" "t4" "t5" "t6" "t7"))
  (start_list "txarea_style")
  (mapcar 'add_list txarea_stylist)
  (end_list)
  (set_tile "txarea_style" txarea_sty)
  (action_tile "txarea_style" "(setq txarea_sty $value)")
  ;decimais
  (setq txarea_declist (list "0" "0.0" "0.00" "0.000" "0.0000" "0.00000"
			     "0.000000" "0.0000000" "0.00000000"))
  (start_list "txarea_decimals")
  (mapcar 'add_list txarea_declist)
  (end_list)
  (set_tile "txarea_decimals" txarea_dec)
  (action_tile "txarea_decimals" "(setq txarea_dec $value)")
  ;unidades
  (setq txarea_untlist (list "mm2" "cm2" "m2" "km2"))
  (start_list "txarea_unit")
  (mapcar 'add_list txarea_untlist)
  (end_list)
  (set_tile "txarea_unit" txarea_und)
  (action_tile "txarea_unit" "(setq txarea_und $value)")
  ;cor do texto
  (start_image "txarea_color")
  (fill_image  0  0
    (dimx_tile "txarea_color")
    (dimy_tile "txarea_color")
    (fix (distof txarea_col))
  )
  (end_image)
  (action_tile "txarea_color" "(txarea_txcol)")
  ;toggle espaço entre o texto e a unidade
  (set_tile "txarea_space" txarea_spc)
  (action_tile "txarea_space" "(setq txarea_spc $value)")
  ;tobble escrever ou não
  (set_tile "txarea_write" txarea_wrt)
  (if (= txarea_wrt "0") (mode_tile "txarea_space" 1))
  (action_tile "txarea_write" "(txa_writexxt)")
  ;estilo do texto de Ambiente
  (start_list "txamb_style")
  (mapcar 'add_list txarea_stylist)
  (end_list)
  (set_tile "txamb_style" txamb_sty)
  (action_tile "txamb_style" "(setq txamb_sty $value)")
  ;Cor do texto do ambiente
  (start_image "txamb_color")
  (fill_image  0  0
    (dimx_tile "txamb_color")
    (dimy_tile "txamb_color")
    (fix (distof txamb_col))
  )
  (end_image)
  (action_tile "txamb_color" "(txamb_txcol)")
  ;ações
  (action_tile "accept" "(done_dialog 1)")
  (action_tile "cancel" "(done_dialog 0)")
  (setq cn_txarea_dialog (start_dialog))
  (unload_dialog dcl_id)
;o que fazer depois
  (if (= 1 cn_txarea_dialog) (cn7_txarea_ok))
)

;ação do toggle "escrever unidade"
(defun txa_writexxt ()
  (setq txarea_wrt $value)
  (if (= txarea_wrt "0")
    (mode_tile "txarea_space" 1)
    (mode_tile "txarea_space" 0)
  )
)

;***************************************************
;botão "OK"
;salva o arquivo
;***************************************************
(defun cn7_txarea_ok ()
  (setq file2 (open (strcat cnp_root "/config/txarea.txt") "w" "utf8"))
  (write-line txarea_sty file2)
  (write-line txarea_dec file2)
  (write-line txarea_und file2)
  (write-line txarea_wrt file2)
  (write-line txarea_col file2)
  (write-line txarea_spc file2)
  (write-line txamb_sty file2)
  (write-line txamb_col file2)
  (close file2)
)

;escolher cor do texto
(defun txarea_txcol ()
  (setq txarea_newcol (acad_colordlg (fix (distof txarea_col))))
  (if (/= nil txarea_newcol) (setq txarea_col (rtos txarea_newcol 2 0)))
  (start_image "txarea_color")
  (fill_image  0  0
    (dimx_tile "txarea_color")
    (dimy_tile "txarea_color")
    (fix (distof txarea_col))
  )
  (end_image)
)

;escolher cor do texto
(defun txamb_txcol ()
  (setq txamb_newcol (acad_colordlg (fix (distof txamb_col))))
  (if (/= nil txamb_newcol) (setq txamb_col (rtos txamb_newcol 2 0)))
  (start_image "txamb_color")
  (fill_image  0  0
    (dimx_tile "txamb_color")
    (dimy_tile "txamb_color")
    (fix (distof txamb_col))
  )
  (end_image)
)



;***********************************************
;Somar áreas
;***********************************************
(defun c:somarea (/ cext ss1 count emax pt1 lprec tarea1 tarea)
  (guarda '("blipmode" "cecolor" "celtype" "clayer" "cmdecho" "orthomode"
	    "textstyle" "luprec" "osmode" ))
  (setvar "cmdecho" 0)
  (while
    (not (setq cext
           (entsel "\nSelecione o contorno externo: "))))
  (prompt "\nSelecione os contornos a adicionar...")      
  (setq ss1 (ssget))
  (if (/= ss1 nil)
    (progn
      (ssdel (car cext) ss1)                          
      (command "._area" "_a" "_e" cext "" "_a" "_e")   
      (setq count 0                                    
            emax (sslength ss1)                        
      )
      (while (< count emax)                             
        (command (ssname ss1 count))                    
        (setq count (1+ count))
                         
      )
    )
    (command "_.area" "_e" cext)
  )
  (command "" "")
  (area_text)
  (devolve)
  (princ)
)

;***********************************************
;Subtrair áreas
;***********************************************
(defun c:subarea (/ cext ss1 count emax pt1 lprec tarea1 tarea)
  (guarda '("blipmode" "cecolor" "celtype" "clayer" "cmdecho" "orthomode"
	    "textstyle" "luprec" "osmode" ))
  (setvar "cmdecho" 0)
  (while
    (not (setq cext
           (entsel "\nSelecione o contorno externo: "))))
  (prompt "\nSelecione os contornos a subtrair...")      
  (setq ss1 (ssget))
  (if (/= ss1 nil)
    (progn
      (ssdel (car cext) ss1)                          
      (command "_.area" "_a" "_e" cext "" "_s" "_e")   
      (setq count 0                                    
            emax (sslength ss1)                        
      )
      (while (< count emax)                             
        (command (ssname ss1 count))                    
        (setq count (1+ count))
                         
      )
    )
    (command "_.area" "_e" cext)
  )
  (command "" "")
  (area_text)
  (devolve)
  (princ)
)

;Mede a última polilinha e escreve sua área *************************
(defun c:plarea ()
  (if (and (/= "LWPOLYLINE" (cdr (assoc 0 (setq last_ent (entget (entlast))))))
	   (/= "POLYLINE" (cdr (assoc 0 (setq last_ent (entget (entlast))))))
      );and
    (progn
      (alert "A última entidade não é uma polyline...")
      (exit)
    )
    (progn
	(command "._area" "_o" (entlast))
	(area_text)
    )
  );if
  (princ)
);defun


;escreve a última área medida
(defun c:ultarea () (area_text)(princ)) 

;Funcao m2: Seleciona um texto e poe m2 como sufixo ***********
;**************************************************************
(defun c:m2 ()
  (cn7_cfg_txarea_file)
  (prompt "\nSelecione o texto a ser acrescido...")
  (setq ent1 (entget (car (entsel))))
  (setq txt1 (cdr (assoc 1 ent1)))
  (cond
    ((= txarea_und "0") (setq newtxt (cons 1 (strcat txt1 "mm2"))))
    ((= txarea_und "1") (setq newtxt (cons 1 (strcat txt1 "cm2"))))
    ((= txarea_und "2") (setq newtxt (cons 1 (strcat txt1 "m2"))))
    ((= txarea_und "3") (setq newtxt (cons 1 (strcat txt1 "km2"))))
  )
  (setq old (assoc 1 ent1))
  (entmod (subst newtxt old ent1))
  (princ)
);defun

;cnp_14


;*************************************************************************************************
;*************************************************************************************************
;Distâncias
;*************************************************************************************************
;*************************************************************************************************

;formatação do texto para distâncias
(defun c:txdist () (cn7_cfgmain_txdist)(princ))

;distribuidor
(defun cn7_cfgmain_txdist ()
  (cn7_cfg_txdist_file)
  (cn7_cfg_txdist)
  (if (= cn7_cfgmain_return 1) (cn7_cfg_main))
)

;lê os valores iniciais da DCL no arquivo de dados
(defun cn7_cfg_txdist_file ()
  (if (findfile (strcat cnp_root "/config/txdist.txt"))
    (cn7_txdist_readfile)
    (progn
      (setq file (open (strcat cnp_root "/config/txdist.txt") "w" "utf8"))
      (write-line "3" file)
      (write-line "2" file)
      (write-line "2" file)
      (write-line "1" file)
      (write-line "2" file)
      (write-line "0" file)
      (close file)
      (cn7_txdist_readfile)
    )
  )
)

;função que lê o arquivo de dados
(defun cn7_txdist_readfile ()
  (setq	file (open (strcat cnp_root "/config/txdist.txt") "r" "utf8"))
  (setq	txdist_sty (read-line file))
  (setq	txdist_dec (read-line file))
  (setq	txdist_und (read-line file))
  (setq	txdist_wrt (read-line file))
  (setq	txdist_col (read-line file))
  (setq	txdist_spc (read-line file))
  (close file)
)

;controle da DCL
(defun cn7_cfg_txdist ()
;abre a dcl
  (setq dcl_id (load_dialog (strcat cnp_root "/lisp/cadnorma.dcl")))
  (if (not (new_dialog "cn7_cfg_txdist" dcl_id)) (exit))
  ;estilo
  (setq txdist_stylist (list "r50" "r60" "r70" "r80" "r90" "r100" "r120" "r140" "r175" "r200"
			    "t1" "t2" "t3" "t4" "t5" "t6" "t7"))
  (start_list "txdist_style")
  (mapcar 'add_list txdist_stylist)
  (end_list)
  (set_tile "txdist_style" txdist_sty)
  (action_tile "txdist_style" "(setq txdist_sty $value)")
  ;decimais
  (setq txdist_declist (list "0" "0.0" "0.00" "0.000" "0.0000" "0.00000"
			     "0.000000" "0.0000000" "0.00000000"))
  (start_list "txdist_decimals")
  (mapcar 'add_list txdist_declist)
  (end_list)
  (set_tile "txdist_decimals" txdist_dec)
  (action_tile "txdist_decimals" "(setq txdist_dec $value)")
  ;unidades
  (setq txdist_untlist (list "mm" "cm" "m" "km"))
  (start_list "txdist_unit")
  (mapcar 'add_list txdist_untlist)
  (end_list)
  (set_tile "txdist_unit" txdist_und)
  (action_tile "txdist_unit" "(setq txdist_und $value)")
  ;cor do texto
  (start_image "txdist_color")
  (fill_image  0  0
    (dimx_tile "txdist_color")
    (dimy_tile "txdist_color")
    (fix (distof txdist_col))
  )
  (end_image)
  (action_tile "txdist_color" "(txdist_txcol)")
  ;tobble escrever ou não
  (set_tile "txdist_write" txdist_wrt)
  (if (= txdist_wrt "0") (mode_tile "txdist_space" 1))
  (action_tile "txdist_write" "(txa_writext)")
  ;toggle espaço entre o texto e a unidade
  (set_tile "txdist_space" txdist_spc)
  (action_tile "txdist_space" "(setq txdist_spc $value)")
  ;ações
  (action_tile "accept" "(done_dialog 1)")
  (action_tile "cancel" "(done_dialog 0)")
  (setq cn_txdist_dialog (start_dialog))
  (unload_dialog dcl_id)
;o que fazer depois
  (if (= 1 cn_txdist_dialog) (cn7_txdist_ok))
)

;ação do toggle "escrever unidade"
(defun txa_writext ()
  (setq txdist_wrt $value)
  (if (= txdist_wrt "0")
    (mode_tile "txdist_space" 1)
    (mode_tile "txdist_space" 0)
  )
)

;***************************************************
;botão "OK"
;salva o arquivo
;***************************************************
(defun cn7_txdist_ok ()
  (setq file2 (open (strcat cnp_root "/config/txdist.txt") "w" "utf8"))
  (write-line txdist_sty file2)
  (write-line txdist_dec file2)
  (write-line txdist_und file2)
  (write-line txdist_wrt file2)
  (write-line txdist_col file2)
  (write-line txdist_spc file2)
  (close file2)
)

;escolher cor do texto
(defun txdist_txcol ()
  (setq txdist_newcol (acad_colordlg (fix (distof txdist_col))))
  (if (/= nil txdist_newcol) (setq txdist_col (rtos txdist_newcol 2 0)))
  (start_image "txdist_color")
  (fill_image  0  0
    (dimx_tile "txdist_color")
    (dimy_tile "txdist_color")
    (fix (distof txdist_col))
  )
  (end_image)
)

(defun dist_text ()
  (cn7_cfg_txdist_file)
  (setq osmo (getvar "osmode"))
  (setvar "osmode" 0)
  (initget 128)
  (setq pt1 (getpoint "\nEditar existente/Formatar texto/<Ponto do texto>..."))
  (setvar "osmode" osmo)
  (cond
    ;se clicar num ponto
    ((= 'LIST (type pt1))
     (dist_find_text)
     (dist_writext)
    )
    ((= 'STR  (type pt1))
     (cond       
       ((= "E" (strcase pt1))
	(prompt "\nSelecione o texto a ser editado... ")
	(setq s2 (entsel))
	(dist_find_text)
	(entmod (subst (cons 1 dist_txt) (assoc 1 (entget (car s2))) (entget (car s2))))
       )
       ((= "F" (strcase pt1))
	(cn7_cfgmain_txdist)
	(dist_text)
       )
       (t
	(prompt "\nOpção inválida... ")
	(devolve)
	(d2p_action)
       )
     )
    )
    (t (exit))
  );cond
)


;encontra o texto exato
(defun dist_find_text ()
  ;decimais
  (setq dist_dec (fix (distof txdist_dec)))
  ;valor
  (setq dist_num (getvar "distance"))
  (cond
    ;se a unidade de desenho é metos
    ((= cn7_dwgunit 1.0)
     (cond
       ((= txdist_und "0") (setq dist_value (* dist_num 1e3) dist_sufix "mm"))
       ((= txdist_und "1") (setq dist_value (* dist_num 1e2) dist_sufix "cm"))
       ((= txdist_und "2") (setq dist_value (* dist_num 1.0) dist_sufix "m"))
       ((= txdist_und "3") (setq dist_value (/ dist_num 1e3) dist_sufix "km"))
     )
    )
    ;se a unidade de desenho é centímetos
    ((= cn7_dwgunit 100.0)
     (cond
       ((= txdist_und "0") (setq dist_value (* dist_num 1e1) dist_sufix "mm"))
       ((= txdist_und "1") (setq dist_value (* dist_num 1.0) dist_sufix "cm"))
       ((= txdist_und "2") (setq dist_value (/ dist_num 1e2) dist_sufix "m"))
       ((= txdist_und "3") (setq dist_value (/ dist_num 1e5) dist_sufix "km"))
     )
    )
    ;se a unidade de desenho é milímetos
    ((= cn7_dwgunit 1000.0)
     (cond
       ((= txdist_und "0") (setq dist_value (* dist_num 1.0) dist_sufix "mm"))
       ((= txdist_und "1") (setq dist_value (/ dist_num 1e1) dist_sufix "cm"))
       ((= txdist_und "2") (setq dist_value (/ dist_num 1e3) dist_sufix "m"))
       ((= txdist_und "3") (setq dist_value (/ dist_num 1e6) dist_sufix "km"))
     )
    )
  );cond
  ;texto final
  (if (= txdist_wrt "0")
    (setq dist_txt (rtos dist_value 2 dist_dec))
    (if (= txdist_spc "0")
      (setq dist_txt (strcat (rtos dist_value 2 dist_dec) dist_sufix))
      (setq dist_txt (strcat (rtos dist_value 2 dist_dec) " " dist_sufix))
    )
  )
)

;escreve, efetivamente, o texto
(defun dist_writext ()
  ;ponto de inserção
  (setq psimb_txt pt1)
  ;estilo
  (setq txdist_stylist (list "r50" "r60" "r70" "r80" "r90" "r100" "r120" "r140" "r175" "r200"
			    "t1" "t2" "t3" "t4" "t5" "t6" "t7"))
  (setq dist_sty (nth (fix (distof txdist_sty)) txdist_stylist))
  (setq dist_ang (/ (* (angle p1 p2) 180.0) pi))
  (if (= nil dist_ang) (setq dist_ang 0.0))
  (cn7_txsimb dist_sty "c" dist_txt (fix (distof txdist_col)) "Distâncias" dist_ang)
)


;mede e escrevea distância entre dois pontos
(defun c:d2p () (d2p_action)(princ))

(defun d2p_action ()
  (guarda '("blipmode" "cecolor" "celtype" "clayer" "cmdecho" "orthomode"
      "textstyle" "luprec" "osmode" ))
  (if dist_style (setq dist_style (strcase dist_style)))
  ;(dist_verify)
  (setq pA (getpoint "\nPrimeiro ponto..."))
  (setq pB (getpoint pa "\nSegundo ponto..."))
  (SETQ P1 (LIST (NTH 0 PA) (NTH 1 PA) 0))
  (SETQ P2 (LIST (NTH 0 PB) (NTH 1 PB) 0))
  (setq ang (angle p1 p2))  (setq ang_txt (/ (* 180 ang) pi))
  (command "._dist" "_non" p1 "_non" p2)
  (setq dist_valor (distance p1 p2))
  (if (/= nil dist_valor) (dist_text))
  (devolve)
);defun

;cnp_15

;*************************************************************************************************
;*************************************************************************************************
;Polylines
;*************************************************************************************************
;*************************************************************************************************


;linemend
(defun c:linemend ( / ent1 ent2 params1 1pt10 2pt10 old10
                      1pt11 2pt11 old11 dist1 dist2 dist3 dist4
                      distlist maxdist pt1 pt10 pt11)
   (setq ent1 (entsel "\nSelecione a 1a linha:  "))
   (setvar "cmdecho" 0)
   (setvar "orthomode" 1)
   (while ent1
      (setq ent1 (car ent1))
      (redraw ent1 3)
      (setq ent2 (car (entsel "\nSelecione a 2a linha...  ")))
      (while (null ent2)
         (prompt "\nNo entity found.")
         (setq ent1 (car (entsel "\nSelect second line:  ")))
         (if (/= (cdr (assoc 0 (entget ent2))) "LINE")
            (progn
               (prompt "\nLines Only!")
               (setq ent2 nil)
            )                                         ;progn
         )                                            ;if
      )                                               ;while

      (redraw ent2 3)
      (setq params1 (entget ent1)
            1pt10 (cdr (setq old10 (assoc 10 params1)))
            1pt11 (cdr (setq old11 (assoc 11 params1)))
            params2 (entget ent2)
            2pt10 (cdr (assoc 10 params2))
            2pt11 (cdr (assoc 11 params2))
            dist1 (distance 1pt10 2pt10)
            dist2 (distance 1pt10 2pt11)
            dist3 (distance 1pt11 2pt10)
            dist4 (distance 1pt11 2pt11)
            distlist
              (list
                 (list dist1 1pt10 2pt10)
                 (list dist2 1pt10 2pt11)
                 (list dist3 1pt11 2pt10)
                 (list dist4 1pt11 2pt11)
              );list
            maxdist (max dist1 dist2 dist3 dist4)
            pts (cdr (assoc maxdist distlist))
            pt10 (car pts)
            pt11 (cadr pts)
            params1 (subst (cons 10 pt10) old10 params1)
            params1 (subst (cons 11 pt11) old11 params1)
      )                                               ;setq calculations

      (entdel ent2)
      (entmod params1)
      (entupd ent1)
      (setq ent1 (entsel "\nSelect first line:  "))
   )                                                  ;while loop

   (setvar "cmdecho" 1)
   (gc) (princ)
)                                                     ;defun



;altera espassura de várias polilinhas
(defun c:plwid ()
  (command "._undo" "_m")
  (setq new_width (getreal "\nEspessura desejada..."))
  (setq s1 (ssget))
  (setq s1_n (sslength s1)
	counter 0
  )
  (repeat s1_n
    (setq ent (ssname s1 counter))
    (setq ent1 (entget ent))
    (if (or (= "LWPOLYLINE" (cdr (assoc 0 ent1)))
	    (= "POLYLINE" (cdr (assoc 0 ent1)))
	)
      (command "._pedit" ent "_w" new_width "")
    )
    (setq counter (1+ counter))
  )
  (princ)
)

;spline para pline via divide (quantidade)
(defun c:spldv ()
  (guarda '("blipmode" "cecolor" "celtype" "clayer" "cmdecho" "orthomode"
      "textstyle" "luprec" "osmode" ))
  (setq osmo (getvar "osmode"))
  (setvar "osmode" 0)
  (setq cmdecho (getvar "CMDECHO"))
  (setvar "CMDECHO" 0)
  (setq blipmode (getvar "BLIPMODE"))
  (setvar "BLIPMODE" 0)
  (setq snapmode (getvar "SNAPMODE"))
  (setvar "SNAPMODE" 0)
  (setq entpick (entsel "\nSelecione uma SPLINE/3DPOLY: "))
  (setq ent (entget (car entpick)))
  (setq sp (cdr (assoc 10 ent)))
  (setq ep (cdr (assoc 10 (reverse ent))))
  (setq spl_dist (getint "\nEntre com o numero de segmentos: "))
  (setq clayer (getvar "CLAYER"))
  (cn7_verylayer "spl" 214)  
;;;  (command "._layer" "_m" "spl" "_c" "7" "" "")
  (princ "\nAgora, espere...")
  (command "_.divide" entpick spl_dist)
  (setq	aws (ssget "X"
		   (list (cons 0 "POINT") (cons 8 "SPL"))
	    )
  )
  (princ ".")
  (setq number (sslength aws))
  (setq count 0)
  (command "_.pline" ep)
  (princ ".")
  (while (< count number)    (setq entnam (ssname aws count))
    (setq ent (entget entnam))
    (setq ins (cdr (assoc 10 ent)))
    (command ins)
    (princ ".")
    (setq count (1+ count))
  )
  (command sp "")
  (command "_.erase" aws entpick "")
;;;  (command "._layer" "_s" clayer "")
;;;  (setvar "CMDECHO" cmdecho)
;;;  (setvar "BLIPMODE" blipmode)
;;;  (setvar "SNAPMODE" snapmode)
;;;  (setvar "osmode" osmo)
  (princ "\nFeito!")
  (devolve)
  (princ)
)


;spline para pline via measure (tamanho)
(defun c:splmu ()
  (guarda '("blipmode" "cecolor" "celtype" "clayer" "cmdecho" "orthomode"
      "textstyle" "luprec" "osmode" ))
  (setq osmo (getvar "osmode"))
  (setvar "osmode" 0)
  (setq cmdecho (getvar "CMDECHO"))
  (setvar "CMDECHO" 0)
  (setq blipmode (getvar "BLIPMODE"))
  (setvar "BLIPMODE" 0)
  (setq snapmode (getvar "SNAPMODE"))
  (setvar "SNAPMODE" 0)
  (setq entpick (entsel "\nSelecione uma SPLINE/3DPOLY: "))
  (setq ent (entget (car entpick)))
  (setq sp (cdr (assoc 10 ent)))
  (setq ep (cdr (assoc 10 (reverse ent))))
  (setq spl_dist (getreal "\nEntre com o tamanho dos segmentos: "))
  (setq clayer (getvar "CLAYER"))
  (cn7_verylayer "spl" 214)
;;;  (command "._layer" "_m" "spl" "_c" "7" "" "")
  (princ "\nAgora, espere...")
  (command "_.measure" entpick spl_dist)
  (setq	aws (ssget "X"
		   (list (cons 0 "POINT") (cons 8 "SPL"))
	    )
  )  (princ ".")
  (setq number (sslength aws))
  (setq count 0)
  (command "_.pline" ep)
  (princ ".")
  (while (< count number)
    (setq entnam (ssname aws count))
    (setq ent (entget entnam))
    (setq ins (cdr (assoc 10 ent)))
    (command ins)
    (princ ".")
    (setq count (1+ count))  )
  (command sp "")
  (command "_.erase" aws entpick "")
;;;  (command "._layer" "_s" clayer "")
;;;  (setvar "CMDECHO" cmdecho)
;;;  (setvar "BLIPMODE" blipmode)
;;;  (setvar "SNAPMODE" snapmode)
;;;  (setvar "osmode" osmo)
  (devolve)
  (princ "\nFeito!")
  (princ)
)


;cnp_16


;**************************************************************
;**************************************************************
;Blocos                                                        
;**************************************************************
;**************************************************************

;escalas blocos
(defun c:blks ()
  (prompt "\nAplicar 'Scale' nos blocos selecionados...")
  (initget "Exemplo Nome Todos")
  (setq resp (getkword "\nSelecionar blocos por Exemplo/Nome/Todos...<E/N/T>..."))
  (cond
    ((= resp "Exemplo") (scl_blk_sample))
    ((= resp "Nome") (scl_blk_name))
    ((= resp "Todos") (scl_blk_all))
  )
  (princ)
)

;***** Seleciona por um exemplo
(defun scl_blk_sample ()
  	(prompt "\nSelecione um bloco exemplo...")
	(setq bk_name (cdr (assoc 2 (entget (car (entsel))))))
  	(setq sel_cond (cons 2 bk_name))
	(prompt "\nSelecione os blocos a serem reduzidos ou ampliados...")
	(setq s1 (ssget '((0 . "INSERT"))))
	(setq rot (getreal "\nFator de escala..."))
	(setq count_limit (sslength s1) counter 0)
	(repeat count_limit
		(setq ent1 (ssname s1 counter))
		(setq ent2 ent1)
		(if (= (cdr (assoc 2 (entget ent1))) bk_name)
			(progn
			  	(setq p0 (cdr (assoc 10 (entget ent1))))
			  	(command "._scale" ent1 "" "_non" p0 rot)
			)
		);if
		(setq counter (1+ counter))
	);repeat
	(princ)
);defun



;*****Seleciona pelo nome
(defun scl_blk_name ()
	(setq bk_name (getstring "\nEntre com o nome do bloco..."))
	(prompt "\nSelecione os blocos a serem reduzidos ou ampliados...")
  	(setq s1 (ssget '((0 . "INSERT"))))
	(setq rot (getreal "\nFator de escala..."))
	(setq count_limit (sslength s1) counter 0)
	(repeat count_limit
		(setq ent1 (ssname s1 counter))
		(setq ent2 ent1)
		(if (= (strcase (cdr (assoc 2 (entget ent1)))) (strcase bk_name))
			(progn
			  	(setq p0 (cdr (assoc 10 (entget ent1))))
			  	(command "._scale" ent1 "" "_non" p0 rot)
			)
		);if
		(setq counter (1+ counter))
	);repeat
	(princ)
);defun

;***** Seleciona todos os blocos
(defun scl_blk_all ()
	(prompt "\nSelecione os blocos a serem reduzidos ou ampliados...")
	(setq s1 (ssget '((0 . "INSERT"))))
	(setq rot (getreal "\nFator de escala..."))
	(setq count_limit (sslength s1) counter 0)
	(repeat count_limit
		(setq ent1 (ssname s1 counter))
		(setq ent2 ent1)
	  	(setq p0 (cdr (assoc 10 (entget ent1))))
		(command "._scale" ent1 "" "_non" p0 rot)
		(setq counter (1+ counter))
	);repeat
	(princ)
);defun


;Rotação nos blocos
(defun c:blkr ()
  (prompt "\nAplicar 'Rotate' nos blocos selecionados...")
  (initget "Exemplo Nome Todos")
  (setq resp (getkword "\nSelecionar blocos por Exemplo/Nome/Todos...<E/N/T>..."))
  (cond
    ((= resp "Exemplo") (rot_blk_sample))
    ((= resp "Nome") (rot_blk_name))
    ((= resp "Todos") (rot_blk_all))
  )
  (princ)
)

;***** Seleciona por um exemplo
(defun rot_blk_sample ()
  	(prompt "\nSelecione um bloco exemplo...")
	(setq bk_name (cdr (assoc 2 (entget (car (entsel))))))
  	(setq sel_cond (cons 2 bk_name))
	(prompt "\nSelecione os blocos a serem rodados...")
	(setq s1 (ssget '((0 . "INSERT"))))
	(setq rot (getreal "\nÂngulo de rotação...<em graus>"))
	(setq count_limit (sslength s1) counter 0)
	(repeat count_limit
		(setq ent1 (ssname s1 counter))
		(setq ent2 ent1)
		(if (= (cdr (assoc 2 (entget ent1))) bk_name)
			(progn
			  	(setq p0 (cdr (assoc 10 (entget ent1))))
			  	(command "._rotate" ent1 "" "_non" p0 rot)
			)
		);if
		(setq counter (1+ counter))
	);repeat
	(princ)
);defun



;***** Seleciona pelo nome
(defun rot_blk_name ()
	(setq bk_name (getstring "\nEntre com o nome do bloco..."))
	(prompt "\nSelecione os blocos a serem rodados...")
  	(setq s1 (ssget '((0 . "INSERT"))))
	(setq rot (getreal "\nÂngulo de rotação...<em graus>"))
	(setq count_limit (sslength s1) counter 0)
	(repeat count_limit
		(setq ent1 (ssname s1 counter))
		(setq ent2 ent1)
		(if (= (strcase (cdr (assoc 2 (entget ent1)))) (strcase bk_name))
			(progn
			  	(setq p0 (cdr (assoc 10 (entget ent1))))
			  	(command "._rotate" ent1 "" "_non" p0 rot)
			)
		);if
		(setq counter (1+ counter))
	);repeat
	(princ)
);defun

;***** seleciona todos os blocos
(defun rot_blk_all ()
	(prompt "\nSelecione os blocos a serem rodados...")
	(setq s1 (ssget '((0 . "INSERT"))))
	(setq rot (getreal "\nÂngulo de rotação...<em graus>"))
	(setq count_limit (sslength s1) counter 0)
	(repeat count_limit
		(setq ent1 (ssname s1 counter))
		(setq ent2 ent1)
	  	(setq p0 (cdr (assoc 10 (entget ent1))))
		(command "._rotate" ent1 "" "_non" p0 rot)
		(setq counter (1+ counter))
	);repeat
	(princ)
);defun


;igualar escala de blocos
(defun c:bks ()
  (prompt "\nSelecione o bloco de referência...")
  (setq blk1_name (car (entsel))
	blk1_ent (entget blk1_name)
	blk1_scale (cdr (assoc 41 blk1_ent))
  )
  (prompt (strcat "\nSelecione os blocos para mesma escala...<" (rtos blk1_scale 2 4) ">...: "))
  (setq s1 (ssget '((0 . "INSERT")))
	s1_len (sslength s1)
	counter 0)
  (repeat s1_len
    (setq ent (ssname s1 counter)
	  ent_list (entget ent)
	  ent_list (entmod (subst (cons 41 blk1_scale) (assoc 41 ent_list) ent_list))
	  ent_list (entmod (subst (cons 42 blk1_scale) (assoc 42 ent_list) ent_list))
	  ent_list (entmod (subst (cons 43 blk1_scale) (assoc 43 ent_list) ent_list)))
    (setq counter (1+ counter))
  )
  (princ)
)

;igualar rotação dos blocos
(defun c:bkr ()
  (prompt "\nSelecione o bloco de referência...")
  (setq blk1 (entsel)
	blk1_name (car blk1)
	blk1_ent (entget blk1_name)
	blk1_rot (cdr (assoc 50 blk1_ent))
  ) 
  (prompt (strcat "\nSelecione os blocos para mesma rotação...<" (rtos blk1_rot 2 4) ">...: "))
  (setq s1 (ssget '((0 . "INSERT")))
	s1_len (sslength s1)
	counter 0) 
  (repeat s1_len
    (setq ent (ssname s1 counter)
	  ent_list (entget ent)
	  ent_list (entmod (subst (cons 50 blk1_rot) (assoc 50 ent_list) ent_list))
    )
    (setq counter (1+ counter))
  )
  (princ)
)

;contar blocos
(defun c:bkc ()
  (prompt "\nSelecione o bloco de referência...")
  (setq ent (car (entsel))
	ent_list (entget ent)
	ent_type (cdr (assoc 0 ent_list))
  )
  (if (/= "INSERT" ent_type)
    (progn
      (alert "A entidade selecionada não é um bloco!")
      (quit)
    )
    (progn
      (setq blk_name (cdr (assoc 2 ent_list))
	    s1 (ssget "_x" '((0 . "INSERT")))
	    s1_len (sslength s1)
	    counter 0
      )
      (setq s2 (ssadd)
	    s3 (ssadd)
	    s4 (ssadd)
      )
      (repeat s1_len
	(setq ent (ssname s1 counter)
	      ent_blkname (cdr (assoc 2 (entget ent)))
	)
	(if (= ent_blkname blk_name)
	  (setq s2 (ssadd ent s2))
	)
	(setq counter (1+ counter))
      )
    )
  )
  (setq s2_len (sslength s2))
  (cn7_alert_yes_no
    "Número total de blocos no desenho:"
    (rtos s2_len 2 0)
    "Deseja quantificar uma área específica?"
  )
  (if (= alert_resp "yes")
    (progn
      (prompt "\nSelecione a área a quantificar...")
      (setq s3 (ssget '((0 . "INSERT")))
	    s3_len (sslength s3)
	    counter 0
      )
      (repeat s3_len
	(setq ent (ssname s3 counter)
	      ent_blkname (cdr (assoc 2 (entget ent)))
	)
	(if (= ent_blkname blk_name)
	  (setq s4 (ssadd ent s4))
	)
	(setq counter (1+ counter))
      )
      (setq s4_len (sslength s4))
      (cn7_alert_ok
	(strcat "Total de blocos no desenho: " (rtos s2_len 2 0))
	""
	(strcat "Número de blocos na área selecionada: " (rtos s4_len 2 0))
      )
    )
  )
  (princ)
)

;purge blocks
(defun c:pub ()
  (command "._purge" "_block" "*" "_n")
  (princ)
)

;cnp_17



;********************************************
;explode atributos para Texto
;********************************************
;seleciona os atributos
(defun very_attribs (
       EN  ;;entity name of INSERT object
       /
       EN2 ;;temporary entity name
       EL  ;;entity list
       )
   ;; Get first attrib entity.
   (setq EN2 (entnext EN)
         EL (entget EN2)
         ATTS nil  ;;note that ATTS is global!
   )
   ;; So long as there are attributes...
   (while (= (cdr (assoc 0 EL)) "ATTRIB")
     ;;build ATTS data list containing tag name
     ;;and attribute value.
     (setq ATTS (cons
                   (list (cdr (assoc 2 EL))
                         (cdr (assoc 1 EL))
                   )
                   ATTS)
           EN2 (entnext EN2)
           EL (entget EN2)
     )
   )
)

;comando principal - explode e guarda os atributos
(defun c:atexp ( /
           EN   ;;entity name
           EL   ;;entity data list
           EN2  ;;another entity name
           )
  (setq EN
    (car
      (entsel "\nSelecione um bloco para explodir: ")))
  (if EN
    (progn  ;;did operator select something?
     (setq EL (entget EN)) ;;what is it?
     (if (= (cdr (assoc 0 EL)) "INSERT")
       (progn
        (setvar "CMDECHO" 0) ;;turn off command
                             ;;viewing.
        ;; Set a marker at the last object
        ;; and save the insert point.
        ;; Variables atexp_ent and atexp_ins
        ;; are both global variables.
        (setq atexp_ent (entlast)
              atexp_ins (cdr (assoc 10 EL))
        )
        ;; Now check to see if there are attribs.
        (if (= (cdr (assoc 66 EL)) 1)
           (very_attribs EN)
           (prompt "\nNenhum atributo associado...")
        )
        ;; Explode the block insert.
        (setq EN2 atexp_ent)
        (command "._explode" EN)
        ;; Go through new objects and look for
        ;; attribute definitions to change to
        ;; text.
        (while EN2
           (setq EL (entget EN2)
                 EN2 (entnext EN2)
           )
           (if (= (cdr (assoc 0 EL)) "ATTDEF")
             (attrib_to_text EL)
           )
        )
     ) (alert "\nO objeto selecionado não é um bloco!"))
  ) (prompt "\nNada foi selecionado!"))
  (princ)
)

;conversão de atributos em texto
(defun attrib_to_text (EL)
   ; register the application ID of the Xdata
   ; for the preserving the attribute definition
   ; information.
   (if (null (tblsearch "APPID" "AEXPLODE"))
      (regapp "AEXPLODE"))
   ; Get rid of the attribute definition, we
   ; are replacing it with the TEXT object.
   (entdel (cdr (assoc -1 EL)))
   (entmake (list
      '(0 . "TEXT")
       (assoc 8 EL) ;layer
       (assoc 10 EL) ;insert point
       (if (assoc 11 EL)
          (assoc 11 EL) ;alignment point
          '(11 0.0 0.0 0.0)
       )
       (assoc 40 EL) ;text size
       (cons 1  ;;text value
          (cadr
            (assoc
              (cdr
                (assoc 2 EL))
              ATTS)))
       (assoc 50 EL) ;rotation
       (assoc 51 EL) ;obliq angle
       (assoc 41 EL) ;width factor
       (assoc 71 EL) ;generation flags
       (assoc 72 EL)
       (assoc 73 EL)
       (assoc 7 EL)  ;text style
       (list -3 ;;extended data attach
         (list "AEXPLODE"
           ; tag name
           (cons 1000 (cdr (assoc 2 EL)))
           ; prompt string
           (cons 1000 (cdr (assoc 3 EL)))
           ; default value
           (cons 1000 (cdr (assoc 1 EL)))
           ; attribute flags
           (cons 1070 (cdr (assoc 70 EL)))
         )
       )
   ))
)


;muda a cor do atributo
(defun c:atcol ()
  (prompt "\nSelecione o atributo para mudar de cor...")
  (command "._attedit" "_y" "" "" "" pause "" "_c" (acad_colordlg 7) "")
  (princ)
)

;muda o ângulo do atributo
(defun c:atang ()
  (prompt "\nSelecione o atributo a rotacionar...")
  (command "._attedit" "_y" "" "" "" pause "")
  (prompt "\nNovo ângulo para o atributo...")
  (command "_a" pause "")
  (princ)
)

;muda a altura do atributo
(defun c:atxh ()
  (prompt "\nSelecione o atributo a rotacionar...")
  (command "._attedit" "_y" "" "" "" pause "")
  (command "_h")
  (princ)
)

;cnp_18


;*************************************************************************************************
;*************************************************************************************************
;*************************************  Seqüências e Contadores  *********************************
;*************************************************************************************************
;*************************************************************************************************
;*************************************************************************************************
;*************************************************************************************************
;Funcao SQ1 (Array Sequencial)
;**************************************************************

(defun c:sq1 ()
  (cn7_init)
  (guarda '("blipmode" "cecolor" "celtype" "clayer" "cmdecho" "orthomode"
      "textstyle" "luprec" "osmode" ))
  (prompt "\nMarque dois pontos para distância e ângulo...")
  (setq
     pt1 (getpoint "\nPrimeiro ponto...")
     pt2 (getpoint pt1 "\nSegundo ponto...")
     dist (distance pt1 pt2)
     ang (angle pt1 pt2)
     inicio (getint "\nPrimeiro Termo...")
     quant (getint "\nNumero de elementos...")
     increm 1
     psimb_txt (getpoint "\nPonto inicial...")
  )
  (setq e1 (rtos inicio 2 0) k1 1)
  (repeat quant
    (cn7_txsimb "r80" "c" e1 2 "Sequências" "0")
    (setq psimb_txt (polar psimb_txt ang dist))
    (setq e1 (rtos (+ inicio (* k1 increm)) 2 0))
    (setq k1 (1+ k1))
  );repeat
  (devolve)
  (princ)
)



;***********************************************************
;Seqüência especial
;***********************************************************
(defun c:txseq ()  (cn7_cfgmain_seq) (princ))

;distribuidor
(defun cn7_cfgmain_seq ()
  (cn7_cfg_txseq_file)
  (cn7_cfg_txseq)
  (if (= cn7_cfgmain_return 1) (cn7_cfg_main))
)


;lê os dados iniciais da DCL no arquivo de dados
(defun cn7_cfg_txseq_file ()
  (if (findfile (strcat cnp_root "/config/txseq.txt"))
    (cn7_txseq_readfile)
    (progn
      (setq file (open (strcat cnp_root "/config/txseq.txt") "w" "utf8"))
      (write-line "3" file)
      (write-line "1" file)
      (write-line "" file)
      (write-line "" file)
      (write-line "0" file)
      (write-line "2" file)
      (close file)
      (cn7_txseq_readfile)
    )
  )
)

;função que lê o arquivo de dados
(defun cn7_txseq_readfile ()
  (setq	file (open (strcat cnp_root "/config/txseq.txt") "r" "utf8"))
  (setq	txseq_sty (read-line file))
  (setq	txseq_inc (read-line file))
  (setq	txseq_pfx (read-line file))
  (setq	txseq_sfx (read-line file))
  (setq	txseq_rot (read-line file))
  (setq	txseq_col (read-line file))
  (close file)
)

(defun cn7_cfg_txseq ()
;abre a dcl
  (setq dcl_id (load_dialog (strcat cnp_root "/lisp/cadnorma.dcl")))
  (if (not (new_dialog "txseq" dcl_id)) (exit))
  ;estilo
  (setq txseq_stylist (list "r50" "r60" "r70" "r80" "r90" "r100" "r120" "r140" "r175" "r200"
			    "t1" "t2" "t3" "t4" "t5" "t6" "t7"))
  (start_list "txseq_style")
  (mapcar 'add_list txseq_stylist)
  (end_list)
  (set_tile "txseq_style" txseq_sty)
  (action_tile "txseq_style" "(setq txseq_sty $value)")
  ;incremento
  (set_tile "txseq_increm" txseq_inc)
  (action_tile "txseq_increm" "(txseq_incremento)")
  ;prefixo
  (set_tile "txseq_prefix" txseq_pfx)
  (action_tile "txseq_prefix" "(setq txseq_pfx $value)")
  ;sufixo
  (set_tile "txseq_sufix" txseq_sfx)
  (action_tile "txseq_sufix" "(setq txseq_sfx $value)")
  ;Rotação
  (set_tile "txseq_rotate" txseq_rot)
  (action_tile "txseq_rotate" "(setq txseq_rot $value)")
  ;cor do texto
  (start_image "txseq_color")
  (fill_image  0  0
    (dimx_tile "txseq_color")
    (dimy_tile "txseq_color")
    (fix (distof txseq_col))
  )
  (end_image)
  (action_tile "txseq_color" "(txseq_txcol)")
  ;ações
  (action_tile "accept" "(done_dialog 1)")
  (action_tile "cancel" "(done_dialog 0)")
  (setq cn_txseq_dialog (start_dialog))
  (unload_dialog dcl_id)
;o que fazer depois
  (if (= 1 cn_txseq_dialog) (cn7_txseq_ok))
)


;***************************************************
;botão "OK"
;salva o arquivo
;***************************************************
(defun cn7_txseq_ok ()
  (setq file2 (open (strcat cnp_root "/config/txseq.txt") "w" "utf8"))
  (write-line txseq_sty file2)
  (write-line txseq_inc file2)
  (write-line txseq_pfx file2)
  (write-line txseq_sfx file2)
  (write-line txseq_rot file2)
  (write-line txseq_col file2)
  (close file2)
)

;incremento
(defun txseq_incremento ()
  (setq txseq_inc $value)
  (if (not (distof txseq_inc));se não é um número
    (progn
      (alert "Você deve digitar\num número inteiro!")
      (mode_tile "txseq_increm" 2)
    )
    (progn
      (setq txseq_inc (rtos (fix (distof txseq_inc)) 2 0))
      (set_tile "txseq_increm" txseq_inc)
    )
  )
)

;escolher cor do texto
(defun txseq_txcol ()
  (setq txseq_newcol (acad_colordlg (fix (distof txseq_col))))
  (if (/= nil txseq_newcol) (setq txseq_col (rtos txseq_newcol 2 0)))
  (start_image "txseq_color")
  (fill_image  0  0
    (dimx_tile "txseq_color")
    (dimy_tile "txseq_color")
    (fix (distof txseq_col))
  )
  (end_image)
)

;iniciar sequência especial
(defun c:sq2 () (cn7_cfg_txseq_file) (sq2_action) (princ))

(defun sq2_action ()
  (cn7_init)
  (guarda '("blipmode" "cecolor" "celtype" "claeiro posyer" "cmdecho" "orthomode"
      "textstyle" "luprec" "osmode" ))
  (initget 128)
  (setq pt1 (getpoint "\nFomatar/Distância e ângulo/<Primeiro ponto para distância e ângulo>... "))
  (cond
    ((= 'LIST (type pt1))
     (setq pt2 (getpoint pt1 "\nSegundo ponto para distância e ângulo...")
	   dist (distance pt1 pt2)
	   ang (angle pt1 pt2))
     (sq2_go)
     )
    ((= 'STR  (type pt1))
     (cond
       ((= "F" (strcase pt1))
	(cn7_cfgmain_seq)
	(sq2_action))
       ((= "D" (strcase pt1))
	(setq dist (getreal "\nEntre com a distância...: ")
	      sq2_ang (getreal "\nEntre com o ângulo (en graus)...: ")
	      ang (/ (* sq2_ang pi) 180.0))
	(sq2_go))
     )
    )
    (t (alert "Opção inválida...\nTente novamente!") (sq2_action))
  );cond
  (devolve)
)

(defun sq2_go ()
  (setq inicio (getint "\nPrimeiro Termo...(ENTER = 1)...")
	quant (getint "\nNumero de elementos...")
	psimb_txt (getpoint "\nPonto inicial..."))
  (if (= nil inicio) (setq inicio 1))
  (if (= txseq_rot "1")
    (setq angtx (/ (* ang 180) pi))
    (setq angtx 0)
  )
  (setq e1 (strcat txseq_pfx (rtos inicio 2 0) txseq_sfx) k1 1)
  (setq txseq_stylist (list "r50" "r60" "r70" "r80" "r90" "r100" "r120" "r140" "r175" "r200"
			    "t1" "t2" "t3" "t4" "t5" "t6" "t7"))
  (setq seq_sty (nth (fix (distof txseq_sty)) txseq_stylist))
  (repeat quant
    (cn7_txsimb seq_sty "c" e1 (fix (distof txseq_col 2)) "Sequencias_2" angtx)
    (setq psimb_txt (polar psimb_txt ang dist))
    (setq inicio (+ inicio (distof txseq_inc)))
    (setq e1 (strcat txseq_pfx (rtos inicio 2 0) txseq_sfx))
    (setq k1 (1+ k1))
  );repeat
  (devolve)
)



;Ets.LSP: Ets lets you convert a series of text objects into a set of
;         sequential numbers.
;****************************************************************
 (defun c:ets ( / txt v1 v2 v3 tp snew new old unt prec)
   (setvar "cmdecho" 0)
   (if (not *uglb)(setq *uglb 2))
   (if (not *prglb)(setq *prglb 0))
   (if (not *incglb)(setq *incglb 1.0))
   (princ "Selecione os números a alterar na ordem desejada: ")
   (setq v1 (ssget '((0 . "TEXT")) ))
   (setq unt 2)
   (setq uglb unt)
   (setq prec (getint (strcat "\nEntre com a precisão... <" (itoa *prglb) ">: ")))
          (if (not prec)
              (setq prec *prglb)(setq *prglb prec)
          )
          (setq inc (getreal (strcat "\nValor do Incremento... <" (rtos *incglb 2 2) ">: ")))
          (if (not inc)
              (setq inc *incglb)(setq *incglb inc)
          )
          (setq new (getreal "\nValor inicial...: "))
          (setq v2 0)
             (if (and v1 new)
                 (while (< v2 (sslength v1))
                        (setq snew (rtos new unt prec))
                        (setq snew (cons 1 snew))
                        (setq txt (ssname v1 v2))
                        (setq old (assoc 1 (setq v3 (entget txt))))
                        (entmod (subst snew old v3))
                        (entupd txt)
                        (setq new (+ new inc))
                        (setq v2 (+ v2 1))
                 )
             )
(princ)
)




;Funcao de Contador k1 ***************************************
;*************************************************************
(defun c:k1 ()
  (cn7_init)
  (guarda '("blipmode" "cecolor" "celtype" "clayer" "cmdecho" "orthomode"
      "textstyle" "luprec" "osmode" ))
  (setq cont-k1 (1+ cont-k1))
  (if (/= nil ang) (setq lastang ang))
  (initget 128)
  (setq psimb_txt (getpoint "\nAtualizar/<Ponto de Inserção>..."))
  (cond
    ((= 'LIST (type psimb_txt))
     (setq ang (getangle psimb_txt "\nÂngulo para o texto...<Enter=último>..."))
     (if (= nil ang)
       (if (/= nil lastang)
	 (setq ang lastang)
	 (setq ang 0)
       )
       (progn
	 (setq ang (/ (* ang 180) pi))
	 (setq lastang ang)
       )
     )
     (cn7_txsimb "r80" "m" (rtos cont-k1 2 0) 2 "Contador" ang)
    )
    ((= 'STR  (type psimb_txt))
     (cond
       ((= "A" (strcase psimb_txt))
	(initget 1)
	(setq cont-k1 (getint "\nPróxima numeração ...<número inteiro>..."))
	(setq psimb_txt (getpoint "\nPonto de Inserção..."))
	(setq ang (getangle psimb_txt "\nÂngulo para o texto...<Enter=último>..."))
	(if (= nil ang) (setq ang 0) (setq ang (/ (* ang 180) pi)))
        (cn7_txsimb "r80" "m" (rtos cont-k1 2 0) 2 "Contador" ang)
       )
       (t (cn7_alert_ok "Opção inválida!" "Marque um ponto ou digite" "'A' para Atualizar o Contador"))
     ))
  )
  (devolve)
  (princ)
);defun




;Funcao de Contador k2 ***************************************
;**************************************************************
(defun c:k2 ()
  (cn7_init)
  (guarda '("blipmode" "cecolor" "celtype" "clayer" "cmdecho" "orthomode"
      "textstyle" "luprec" "osmode" ))
  (setq cont-k2 (1+ cont-k2))
  (if (/= nil ang) (setq lastang ang))
  (initget 128)
  (setq psimb_txt (getpoint "\nAtualizar/<Ponto de Inserção>..."))
  (cond
    ((= 'LIST (type psimb_txt))
     (setq ang (getangle psimb_txt "\nÂngulo para o texto...<Enter=último>..."))
     (if (= nil ang)
       (if (/= nil lastang)
	 (setq ang lastang)
	 (setq ang 0)
       )
       (progn
	 (setq ang (/ (* ang 180) pi))
	 (setq lastang ang)
       )
     )
     (cn7_txsimb "r80" "m" (rtos cont-k2 2 0) 2 "Contador2" ang)
     (setq grp_type "2")
     (cn7_find_blkscl)
     (cn7_verylayer (strcat cn7_blk_prefixlay "Contador2") "2")
     (command "._circle" psimb_txt (* 0.25 cn7_blkscl))
    )
    ((= 'STR  (type psimb_txt))
     (cond
       ((= "A" (strcase psimb_txt))
	(initget 1)
	(setq cont-k2 (getint "\nPróxima numeração ...<número inteiro>..."))
	(setq psimb_txt (getpoint "\nPonto de Inserção..."))
	(setq ang (getangle psimb_txt "\nÂngulo para o texto...<Enter=último>..."))
	(if (= nil ang) (setq ang 0)(setq ang (/ (* ang 180) pi)))
        (cn7_txsimb "r80" "m" (rtos cont-k2 2 0) 2 "Contador2" ang)
	(setq grp_type "2")
	(cn7_find_blkscl)
	(cn7_verylayer (strcat cn7_blk_prefixlay "Contador2") "2")
	(command "._circle" psimb_txt (* 0.25 cn7_blkscl))
       )
       (t (cn7_alert_ok "Opção inválida!" "Marque um ponto ou digite" "'A' para Atualizar o Contador"))
     ))
  )
  (devolve)
  (princ)
)


;**************************************************************
;Funcao de Contador k3 ***************************************
;**************************************************************
(defun c:k3 ()
  (cn7_altext_readfile)
  (cn7_init)
  (cn7_cfg_k3_file)
  (setq cont-k3 (1+ cont-k3))
  (setq k3_stylist (list "r50" "r60" "r70" "r80" "r90" "r100" "r120" "r140" "r175" "r200"
			    "t1" "t2" "t3" "t4" "t5" "t6" "t7")
	k3_aliglist (list "Left" "Center" "Middle" "Rigth")
	k3_formlist (list "1" "01" "001" "0001")
  )
  (k3_action)
  (princ)
)

;escreve o texto
(defun k3_wrtext ()
  (setq psimb_txt pt1)
     (setq ang (getangle psimb_txt "\nÂngulo para o texto...(Enter=0 ou último)..."))
     (if (= nil ang)
       (if (/= nil lastang)
	 (setq ang lastang)
	 (setq ang 0)
       )
       (progn
	 (setq ang (/ (* ang 180) pi))
	 (setq lastang ang)
       )
     )
  ;formato do texto principal
  (cond
    ((= k3_frm "0")
     (setq k3-txt (strcat k3_pfx (rtos cont-k3 2 0) k3_sfx))
    )
    ((= k3_frm "1")
     (if (= 1 (strlen (rtos cont-k3 2 0))) (setq k3-txt (strcat k3_pfx "0" (rtos cont-k3 2 0) k3_sfx)))
     (if (= 2 (strlen (rtos cont-k3 2 0))) (setq k3-txt (strcat k3_pfx (rtos cont-k3 2 0) k3_sfx)))
    )
    ((= k3_frm "2")
     (if (= 1 (strlen (rtos cont-k3 2 0))) (setq k3-txt (strcat k3_pfx "00" (rtos cont-k3 2 0) k3_sfx)))
     (if (= 2 (strlen (rtos cont-k3 2 0))) (setq k3-txt (strcat k3_pfx "0" (rtos cont-k3 2 0) k3_sfx)))
     (if (= 3 (strlen (rtos cont-k3 2 0))) (setq k3-txt (strcat k3_pfx (rtos cont-k3 2 0) k3_sfx)))
    )
    ((= k3_frm "3")
     (if (= 1 (strlen (rtos cont-k3 2 0))) (setq k3-txt (strcat k3_pfx "000" (rtos cont-k3 2 0) k3_sfx)))
     (if (= 2 (strlen (rtos cont-k3 2 0))) (setq k3-txt (strcat k3_pfx "00" (rtos cont-k3 2 0) k3_sfx)))
     (if (= 3 (strlen (rtos cont-k3 2 0))) (setq k3-txt (strcat k3_pfx "0" (rtos cont-k3 2 0) k3_sfx)))
     (if (= 4 (strlen (rtos cont-k3 2 0))) (setq k3-txt (strcat k3_pfx (rtos cont-k3 2 0) k3_sfx)))
    )
  )
  ;definição do estilo de texto
  (setq k3_txsty (nth (fix (distof k3_sty)) k3_stylist))
  (cond
    ((= k3_ali "0") (setq k3_txali "_l"))
    ((= k3_ali "1") (setq k3_txali "_c"))
    ((= k3_ali "2") (setq k3_txali "_m"))
    ((= k3_ali "3") (setq k3_txali "_r"))
  )
  (cn7_txsimb k3_txsty k3_txali k3-txt (fix (distof k3_col)) "Contador3" ang)
)


;execução do comando
(defun k3_action ()
  (prompt (strcat "\nPróximo item = " (rtos cont-k3 2 0) "."))
  (initget 128)
  (setq pt1 (getpoint "\nFomatar/Atualizar/<Ponto de Inserção>... "))
  (cond
    ((= 'LIST (type pt1))
     (k3_wrtext)
     )
    ((= 'STR  (type pt1))
     (cond
       ((= "F" (strcase pt1))
	(cn7_cfg_k3)
	(k3_action)
       )
       ((= "A" (strcase pt1))
	(initget 1)
	(setq cont-k3 (getint "\nPróxima numeração ...<número inteiro>..."))
	(k3_action)
       )
     )
    );cond
    (t (alert "Opção inválida...\nTente novamente!") (k3_action))
  );cond
)

(defun cn7_cfg_k3 ()
;abre a dcl
  (setq dcl_id (load_dialog (strcat cnp_root "/lisp/cadnorma.dcl")))
  (if (not (new_dialog "k3" dcl_id)) (exit))
  ;estilo
  (start_list "k3_style")
  (mapcar 'add_list k3_stylist)
  (end_list)
  (set_tile "k3_style" k3_sty)
  (action_tile "k3_style" "(setq k3_sty $value)")
  ;alinhamento
  (start_list "k3_align")
  (mapcar 'add_list k3_aliglist)
  (end_list)
  (set_tile "k3_align" k3_ali)
  (action_tile "k3_align" "(setq k3_ali $value)")
  ;prefixo
  (set_tile "k3_prefix" k3_pfx)
  (action_tile "k3_prefix" "(setq k3_pfx $value)")
  ;sufixo
  (set_tile "k3_sufix" k3_sfx)
  (action_tile "k3_sufix" "(setq k3_sfx $value)")
  ;formato
  (start_list "k3_format")
  (mapcar 'add_list k3_formlist)
  (end_list)
  (set_tile "k3_format" k3_frm)
  (action_tile "k3_format" "(setq k3_frm $value)")
  ;cor do texto
  (start_image "k3_color")
  (fill_image  0  0
    (dimx_tile "k3_color")
    (dimy_tile "k3_color")
    (fix (distof k3_col))
  )
  (end_image)
  (action_tile "k3_color" "(k3_txcol)")
  ;ações
  (action_tile "accept" "(done_dialog 1)")
  (action_tile "cancel" "(done_dialog 0)")
  (setq k3_dialog (start_dialog))
  (unload_dialog dcl_id)
;o que fazer depois
  (if (= 1 k3_dialog) (cn10_k3_ok))
)

;escolher cor do texto
(defun k3_txcol ()
  (setq k3_newcol (acad_colordlg (fix (distof k3_col))))
  (if (/= nil k3_newcol) (setq k3_col (rtos k3_newcol 2 0)))
  (start_image "k3_color")
  (fill_image  0  0
    (dimx_tile "k3_color")
    (dimy_tile "k3_color")
    (fix (distof k3_col))
  )
  (end_image)
)

;salva o arquivo de configuração
(defun cn10_k3_ok ()
  (setq file2 (open (strcat cnp_root "/config/k3.txt") "w" "utf8"))
  (write-line k3_sty file2)
  (write-line k3_ali file2)
  (write-line k3_pfx file2)
  (write-line k3_sfx file2)
  (write-line k3_frm file2)
  (write-line k3_col file2)
  (close file2)
)



;lê os dados iniciais da DCL no arquivo de dados
(defun cn7_cfg_k3_file ()
  (if (findfile (strcat cnp_root "/config/k3.txt"))
    (cn7_k3_readfile)
    (progn
      (setq file (open (strcat cnp_root "/config/k3.txt") "w" "utf8"))
      (write-line "7" file)
      (write-line "0" file)
      (write-line "" file)
      (write-line "" file)
      (write-line "2" file)
      (write-line "4" file)
      (close file)
      (cn7_txseq_readfile)
    )
  )
)

;função que lê o arquivo de dados
(defun cn7_k3_readfile ()
  (setq	file (open (strcat cnp_root "/config/k3.txt") "r" "utf8"))
  (setq	k3_sty (read-line file))
  (setq	k3_ali (read-line file))
  (setq	k3_pfx (read-line file))
  (setq	k3_sfx (read-line file))
  (setq	k3_frm (read-line file))
  (setq	k3_col (read-line file))
  (close file)
)

;cnp_19


;********************************************************************
;********************************************************************
;Chamadas
;********************************************************************
;********************************************************************

;chamada com círculo
(defun c:chc ()
  (cn7_init)
  (guarda '("blipmode" "cecolor" "celtype" "clayer" "cmdecho" "orthomode"
      "textstyle" "luprec" "osmode" ))
  (setq psimb_txt (getpoint "\nPonto de inserção do identificador... "))
  (setq dcl_id (load_dialog (strcat cnp_root "/lisp/cadnorma.dcl")))
  (if (not (new_dialog "chamada" dcl_id)) (exit))
  (if (/= nil chamada_idtx) (set_tile "chamada_id" chamada_idtx))
  (mode_tile "chamada_id" 2)
  (action_tile "chamada_id" "(setq chamada_idtx $value)")
  (action_tile "accept" "(done_dialog 1)")
  (action_tile "cancel" "(done_dialog 0)")
  (setq chamada_dialog (start_dialog))
  (unload_dialog dcl_id)
;o que fazer depois
  (if (= 1 chamada_dialog)
    (progn
      (setq grp_type "2")
      (cn7_find_blkscl)
      (cn7_verylayer (strcat cn7_blk_prefixlay "Chamadas") 1)
      (command "._circle" psimb_txt (* cn7_blkscl 0.25))
      (cn7_txsimb "r80" "m" chamada_idtx 1 "Chamadas" "0")
    )
    (exit)
  )
  (devolve)
  (chamada)
  (princ)
)

;chamada com quadrado
(defun c:chq ()
  (cn7_init)
  (guarda '("blipmode" "cecolor" "celtype" "clayer" "cmdecho" "orthomode"
      "textstyle" "luprec" "osmode" ))
  (setq psimb_txt (getpoint "\nPonto de inserção do identificador... "))
  (setq dcl_id (load_dialog (strcat cnp_root "/lisp/cadnorma.dcl")))
  (if (not (new_dialog "chamada" dcl_id)) (exit))
  (if (/= nil chamada_idtx) (set_tile "chamada_id" chamada_idtx))
  (mode_tile "chamada_id" 2)
  (action_tile "chamada_id" "(setq chamada_idtx $value)")
  (action_tile "accept" "(done_dialog 1)")
  (action_tile "cancel" "(done_dialog 0)")
  (setq chamada_dialog (start_dialog))
  (unload_dialog dcl_id)
;o que fazer depois
  (if (= 1 chamada_dialog)
    (progn
      (setq grp_type "2")
      (cn7_find_blkscl)
      (cn7_verylayer (strcat cn7_blk_prefixlay "Chamadas") 1)
      (if (= 1 (getvar "tilemode"));no Model
	(progn
	  (setq pt1 (polar psimb_txt (/ (* 5 pi) 4) (* 0.3 cn7_blkscl))
		pt2 (polar pt1 (/ pi 4) (* 0.6 cn7_blkscl))
	  )
	)
	(progn
	  (if (= 1 (getvar "cvport"));Paper Space
	    (setq pt1 (polar psimb_txt (/ (* 5 pi) 4) 3)
		pt2 (polar pt1 (/ pi 4) 6)
	    )
	    ;viewport
	    (setq pt1 (polar psimb_txt (/ (* 5 pi) 4) (* 0.3 cn7_blkscl))
		pt2 (polar pt1 (/ pi 4) (* 0.6 cn7_blkscl))
	    )
	 )
       )
      )
      (command "._rectangle" "_non" pt1 "_non" pt2)
      (cn7_txsimb "r80" "m" chamada_idtx 1 "Chamadas" "0")
    )
    (exit)
  )
  (chamada)
  (devolve)
  (princ)
)

;chamada com destaque
(defun c:chd ()
  (cn7_init)
  (guarda '("blipmode" "cecolor" "celtype" "clayer" "cmdecho" "orthomode"
      "textstyle" "luprec" "osmode" ))
  (setq pt1 (getpoint "\nPonto de inserção do identificador... "))
  (setq dcl_id (load_dialog (strcat cnp_root "/lisp/cadnorma.dcl")))
  (if (not (new_dialog "chamada" dcl_id)) (exit))
  (if (/= nil chamada_idtx) (set_tile "chamada_id" chamada_idtx))
  (mode_tile "chamada_id" 2)
  (action_tile "chamada_id" "(setq chamada_idtx $value)")
  (action_tile "accept" "(done_dialog 1)")
  (action_tile "cancel" "(done_dialog 0)")
  (setq chamada_dialog (start_dialog))
  (unload_dialog dcl_id)
;o que fazer depois
  (if (= 1 chamada_dialog)
    (progn
      (setq colmo (getvar "cecolor"))
      (setq grp_type "2")
      (cn7_find_blkscl)
      (cn7_verylayer (strcat cn7_blk_prefixlay "Chamadas") 1)
      (setq pt2 (polar pt1 0 (* cn7_blkscl 0.75))
	    pt3 (polar pt1 0 (/ (* cn7_blkscl 0.75) 2))
	    psimb_txt (polar pt3 (/ pi 2) (* cn7_blkscl 0.1)))
      (setvar "cecolor" "5")
      (command "._line" "_non" pt1 "_non" pt2 "")
      (setvar "cecolor" "4")
      (cn7_txsimb "r120" "c" chamada_idtx 1 "Chamadas" "0")
      (setvar "cecolor" colmo)
    )
    (exit)
  )
  (chamada)
  (devolve)
  (princ)
)


;após inserir o símbolo, decidir se desenha ou não a chamada
;e se ela será em linha ou em arco
(defun chamada ()
  (guarda '("blipmode" "cecolor" "celtype" "clayer" "cmdecho" "orthomode"
	    "textstyle" "luprec" "osmode" ))
  (initget "Linha Arco Nenhum")
  (if (not chamada_atual)
    (progn
      (setq chamada_atual (getkword "\n<Linha>/Arco/Nenhum...: "))
      (if (= chamada_atual nil) (setq chamada_atual "Linha"))
    )
    (progn
      (cond
	((= chamada_atual "Linha")
	 (setq chamada_nova (getkword "\n<Linha>/Arco/Nenhum...: "))
	 (if (/= nil chamada_nova) (setq chamada_atual chamada_nova))
	)
	((= chamada_atual "Arco")
	 (setq chamada_nova (getkword "\nLinha/<Arco>/Nenhum...: "))
	 (if (/= nil chamada_nova) (setq chamada_atual chamada_nova))
	)
	((= chamada_atual "Nenhum")
	 (setq chamada_nova (getkword "\nLinha/Arco/<Nenhum>...: "))
	 (if (/= nil chamada_nova) (setq chamada_atual chamada_nova))
	)
      )
    )
  )
  (cond
    ((= chamada_atual "Arco") (cha_action))
    ((= chamada_atual "Linha")(chl_action))
;;;    (t (exit))
  )
  (princ)
)

;************************************************
;define o apontador
;************************************************
(defun c:apo ()
  (cn7_cfgmain_apo)
  (princ)
)

(defun cn7_cfgmain_apo ()
  (cn7_cfg_apo_file)
  (cn7_cfg_apo)
  (if (= cn7_cfgmain_return 1) (cn7_cfg_main))
)


;lê os dados iniciais da DCL no arquivo de dados
(defun cn7_cfg_apo_file ()
  (if (findfile (strcat cnp_root "/config/pointer.txt"))
    (cn7_apo_readfile)
    (progn
      (setq file (open (strcat cnp_root "/config/pointer.txt") "w" "utf8"))
      (write-line "apo_closed" file)
      (close file)
      (cn7_apo_readfile)
    )
  )
)

;função que lê o arquivo de dados
(defun cn7_apo_readfile ()
  (setq	file (open (strcat cnp_root "/config/pointer.txt") "r" "utf8"))
  (setq	apo_sty (read-line file))
  (close file)
)

(defun cn7_cfg_apo ()
  ;abre a dcl
  (setq dcl_id (load_dialog (strcat cnp_root "/lisp/cadnorma.dcl")))
  (if (not (new_dialog "apontador" dcl_id)) (exit))
  (set_tile "apo_radiokey" apo_sty)
  ;valor inicial do slide
  (setq x (dimx_tile "apo_imagem")
	y (dimy_tile "apo_imagem"))
  (start_image "apo_imagem")
  (cond
    ((= apo_sty "apo_closed") (slide_image 0 0 x y (strcat cnp_root "/slides/Pointer_closed.sld")))
    ((= apo_sty "apo_open") (slide_image 0 0 x y (strcat cnp_root "/slides/Pointer_open.sld")))
    ((= apo_sty "apo_dot") (slide_image 0 0 x y (strcat cnp_root "/slides/Pointer_dot.sld")))
    ((= apo_sty "apo_elipse") (slide_image 0 0 x y (strcat cnp_root "/slides/Pointer_elipse.sld")))
    ((= apo_sty "apo_none") (slide_image 0 0 x y (strcat cnp_root "/slides/Pointer_none.sld")))
  )
  (end_image)
  (action_tile "apo_radiokey" "(apo_radiokey_action)")
  (action_tile "accept" "(done_dialog 1)")
  (action_tile "cancel" "(done_dialog 0)")
  (setq cn_apo_dialog (start_dialog))
  (unload_dialog dcl_id)
  ;o que fazer depois
  (if (= 1 cn_apo_dialog) (cn7_apo_ok))
)

(defun apo_radiokey_action ()
  (setq apo_sty $value)
  (setq x (dimx_tile "apo_imagem")
	y (dimy_tile "apo_imagem"))
  (start_image "apo_imagem")
  (fill_image 0 0 x y -2)
  (cond
    ((= apo_sty "apo_closed") (slide_image 0 0 x y (strcat cnp_root "/slides/Pointer_closed.sld")))
    ((= apo_sty "apo_open") (slide_image 0 0 x y (strcat cnp_root "/slides/Pointer_open.sld")))
    ((= apo_sty "apo_dot") (slide_image 0 0 x y (strcat cnp_root "/slides/Pointer_dot.sld")))
    ((= apo_sty "apo_elipse") (slide_image 0 0 x y (strcat cnp_root "/slides/Pointer_elipse.sld")))
    ((= apo_sty "apo_none") (slide_image 0 0 x y (strcat cnp_root "/slides/Pointer_none.sld")))
  )
  (end_image)
)

;botão "OK"
;salva o arquivo
(defun cn7_apo_ok ()
  (setq file2 (open (strcat cnp_root "/config/pointer.txt") "w" "utf8"))
  (write-line apo_sty file2)
  (close file2)
)


;chamada em linha
(defun c:chl () (chl_action) (princ))

(defun chl_action ()
  (guarda '("blipmode" "cecolor" "celtype" "clayer" "cmdecho" "orthomode"
          "textstyle" "luprec" "osmode" ))
  (cn7_cfg_apo_file)
  (initget 128)
  (if (/= apo_sty "apo_elipse")
    (setq pt1 (getpoint "\nApontador/<Ponto inicial>... "))
    (setq pt1 (getpoint "\nApontador/<Primeiro ponto da Elipse>... "))
  )
  (cond
    ((= 'LIST (type pt1))
     (setq grp_type "2")
     (cn7_find_blkscl)
     (cn7_verylayer (strcat cn7_blk_prefixlay "Chamadas") 1)
     (if (/= apo_sty "apo_elipse")
       (chl_action_draw1)
       (chl_action_draw2)
     )
    )
    ((= 'STR  (type pt1))
     (cond
       ((= "A" (strcase pt1))
	(cn7_cfgmain_apo)
	(chl_action)
       )
       (t
	(alert "Opção Inválida!\nClique num ponto ou didite 'A'\npara configurar o Apontador!")
	(chl_action)
       )
     )
   )
  );cond
  (devolve)
  (princ)
)

;desenha sem elipse
(defun chl_action_draw1 ()
  (setq pt2 (getpoint pt1 "\nPróximo ponto... "))
  (cn7_verylayer (strcat cn7_blk_prefixlay "Chamadas") 1)
  (cond
    ((= apo_sty "apo_closed") (command "_insert" (strcat cnp_root "/blocos/apo_closed") "_s" cn7_blkscl "_non" pt1 "_non" pt2))
    ((= apo_sty "apo_open") (command "_insert" (strcat cnp_root "/blocos/apo_open") "_s" cn7_blkscl "_non" pt1 "_non" pt2))
    ((= apo_sty "apo_dot") (command "_insert" (strcat cnp_root "/blocos/apo_dot") "_s" cn7_blkscl "_non" pt1 "_non" pt2))
    )
  (command "._line" "_non" pt1 "_non" pt2)
  (while (/= nil (setq pt2 (getpoint pt2 "\nPróximo ponto... ")))
    (command "_non" pt2)
    )
  (command "")
)

;desenha com elipse
(defun chl_action_draw2 ()
  (setq pt2 (getpoint pt1 "\nSegundo ponto da Elipse... ")
	pt3 (polar pt1 (angle pt1 pt2) (/ (distance pt1 pt2) 2))
	pt3 (polar pt3 (+ (angle pt1 pt2) (/ pi 2)) (/ (distance pt1 pt2) 6))
  )
  (command "._ellipse" "_non" pt1 "_non" pt2 "_non" pt3 "._line" "_non" pt2)
  (while (/= nil (setq pt2 (getpoint pt2 "\nPróximo ponto... ")))
    (command "_non" pt2)
  )
  (command "")
)

;chamada em arco
(defun c:cha () (cha_action) (princ))

(defun cha_action ()
  (guarda '("blipmode" "cecolor" "celtype" "clayer" "cmdecho" "orthomode"
          "textstyle" "luprec" "osmode" ))
  (cn7_cfg_apo_file)
  (initget 128)
  (if (/= apo_sty "apo_elipse")
    (setq pt1 (getpoint "\nApontador/<Ponto inicial>... "))
    (setq pt1 (getpoint "\nApontador/<Primeiro ponto da Elipse>... "))
  )
  (cond
    ((= 'LIST (type pt1))
     (setq grp_type "2")
     (cn7_find_blkscl)
     (cn7_verylayer (strcat cn7_blk_prefixlay "Chamadas") 1)
     (if (/= apo_sty "apo_elipse")
       (cha_action_draw1)
       (cha_action_draw2)
     )
    )
    ((= 'STR  (type pt1))
     (cond
       ((= "A" (strcase pt1))
	(cn7_cfgmain_apo)
	(cha_action)
       )
       (t
	(alert "Opção Inválida!\nClique num ponto ou didite 'A'\npara configurar o Apontador!")
	(cha_action)
       )
     )
   )
  );cond
  (devolve)
  (princ)
)

;desenha sem elipse
(defun cha_action_draw1 ()
  (setq pt2 (getpoint pt1 "\nPonto final do arco... "))
  (command "._arc" pt1 "_e" pt2 "_d" pause)
  (setq arc (entget (entlast)))
  (setq ang1 (cdr (assoc 50 arc)))
  (setq ang2 (cdr (assoc 51 arc)))
  (setq cen (cdr (assoc 10 arc)))
  (setq ang1b (angle cen pt1))
  (setq ang2b (angle cen pt2))
  (setq val1 (angtos ang1 2 4))
  (setq val2 (angtos ang2 2 4))
  (setq val1b (angtos ang1b 2 4))
  (setq val2b (angtos ang2b 2 4))
  (if (= val1b val1)
    (progn
      (setq angc (+ (/ (* -90 pi) 180) ang1))
      (setq angf (+ (/ (* 90 pi) 180) ang2)))
    )
  (if (= val1b val2)
    (progn
      (setq angc (+ (/ (* 90 pi) 180) ang2))
      (setq angf (+ (/ (* -90 pi) 180) ang1)))
    )
  (setq cf "C")
  (if (= (strcase cf) "C")
    (progn
      (setq angs angc)
      (setq ps pt1) (setq pt pt2)
      ))
  (if (= (strcase cf) "F")
    (progn
      (setq angs angf)
      (setq ps pt2) (setq pt pt1)
      ))
  (setq rots (angtos (+ pi angs) 2 3))
  (cond
    ((= apo_sty "apo_closed") (command "_insert" (strcat cnp_root "/blocos/apo_closed") "_non" ps cn7_blkscl "" rots))
    ((= apo_sty "apo_open") (command "_insert" (strcat cnp_root "/blocos/apo_open") "_non" ps cn7_blkscl "" rots))
    ((= apo_sty "apo_dot") (command "_insert" (strcat cnp_root "/blocos/apo_dot") "_non" ps cn7_blkscl "" rots))
  )
)

;desenha com elipse
(defun cha_action_draw2 ()
  (setq pt2 (getpoint pt1 "\nSegundo ponto da Elipse... ")
	pt3 (polar pt1 (angle pt1 pt2) (/ (distance pt1 pt2) 2))
	pt3 (polar pt3 (+ (angle pt1 pt2) (/ pi 2)) (/ (distance pt1 pt2) 6))
  )
  (command "._ellipse" "_non" pt1 "_non" pt2 "_non" pt3)
  (setq pt4 (getpoint pt2 "\nPonto final do arco... "))
  (command "._arc" pt2 "_e" pt4 "_d" pause)
)


;cnp_20


;******************************************************************************
;******************************************************************************
;Biblioteca
;******************************************************************************
;******************************************************************************

(defun not_yet ()
  (cn7_alert_ok
	"Biblioteca ainda não disponível!"
	"Aguarde novas atualizações."
	"Usuários registrados serão informados.")
)

;Biblioteca do Usuário
;administrador
(defun c:usa ()
  (cn7_init)
  (if (or (= lib_blkfam nil)
	  (and (/= lib_blkfam "sg") (/= lib_blkfam "aq") (/= lib_blkfam "el") (/= lib_blkfam "tu")
	       (/= lib_blkfam "ic") (/= lib_blkfam "sg") (/= lib_blkfam "tl") (/= lib_blkfam "ac")
	       (/= lib_blkfam "cc") (/= lib_blkfam "mt") (/= lib_blkfam "tp")))
    (setq lib_blkfam "sg")
  )
  (setq lib_blkpfx cnp_user ;"cnus"
	lib_type "admin"
  )
  (net_lib_lastlib_readfile)
  (net_lib_cfgmain_lib)
  (princ)
)

;usuário
(defun c:usu ()
  (cn7_init)
  (if (or (= lib_blkfam nil)
	  (and (/= lib_blkfam "sg") (/= lib_blkfam "aq") (/= lib_blkfam "el") (/= lib_blkfam "tu")
	       (/= lib_blkfam "ic") (/= lib_blkfam "sg") (/= lib_blkfam "tl") (/= lib_blkfam "ac")
	       (/= lib_blkfam "cc") (/= lib_blkfam "mt") (/= lib_blkfam "tp")))
    (setq lib_blkfam "sg")
  )
  (setq lib_blkpfx cnp_user ;"cnus"
	lib_type "user"
  )
  (net_lib_lastlib_readfile)
  (net_lib_cfgmain_lib)
  (princ)
)


;Biblioteca Cadnorma
(defun c:lib ()
  (cn7_init)
  (if (or (= lib_blkfam nil)
	  (and (/= lib_blkfam "sg") (/= lib_blkfam "aq") (/= lib_blkfam "el") (/= lib_blkfam "tu")
	       (/= lib_blkfam "ic") (/= lib_blkfam "sg") (/= lib_blkfam "tl") (/= lib_blkfam "ac")
	       (/= lib_blkfam "cc") (/= lib_blkfam "mt") (/= lib_blkfam "tp")))
    (setq lib_blkfam "sg")
  )  
  (setq lib_blkpfx "cadn"
	lib_type "user"
  )
  (lib_lastlib_readfile)
  (lib_cfgmain_lib)
)

;preenche o tipo biblioteca
(defun lib_label ()
  (setq lib_full_list (list "Símbolos Gerais"
			    "Arquitetura"
			    "Elétrica"
			    "Tubulações"
			    "Incêndio e SPDA"
			    "Baixa Tensão"
			    "Ar Condicionado"
			    "Estruturas de Concreto"
			    "Estruturas Metálicas"
			    "Topografia, Geologia e Mapas"
		       )
  )
  (start_list "newlib_label")
  (mapcar 'add_list lib_full_list)
  (end_list)
  (cond
    ((= lib_blkfam "sg")
     (setq lib_blkfam_code "0")
    )
    ((= lib_blkfam "aq")
     (setq lib_blkfam_code "1")
    )
    ((= lib_blkfam "el")
     (setq lib_blkfam_code "2")
    )
    ((= lib_blkfam "tu")
     (setq lib_blkfam_code "3")
    )
    ((= lib_blkfam "ic")
     (setq lib_blkfam_code "4")
    )
    ((= lib_blkfam "tl")
     (setq lib_blkfam_code "5")
    )
    ((= lib_blkfam "ac")
     (setq lib_blkfam_code "6")
    )
    ((= lib_blkfam "cc")
     (setq lib_blkfam_code "7")
    )
    ((= lib_blkfam "mt")
     (setq lib_blkfam_code "8")
    )
    ((= lib_blkfam "tp")
     (setq lib_blkfam_code "9")
    )
  )
  (set_tile "newlib_label" lib_blkfam_code)
  (action_tile "newlib_label" "(new_label_action)")
)

;label para gerenciador de bibliotecas
(defun lib_mng_label ()
  (setq lib_full_list (list "Símbolos Gerais"
			    "Arquitetura"
			    "Elétrica"
			    "Tubulações"
			    "Incêndio e SPDA"
			    "Baixa Tensão"
			    "Ar Condicionado"
			    "Estruturas de Concreto"
			    "Estruturas Metálicas"
			    "Topografia, Geologia e Mapas"
		       )
  )
  (start_list "newlib_label")
  (mapcar 'add_list lib_full_list)
  (end_list)
  (cond
    ((= lib_blkfam "sg")
     (setq lib_blkfam_code "0")
    )
    ((= lib_blkfam "aq")
     (setq lib_blkfam_code "1")
    )
    ((= lib_blkfam "el")
     (setq lib_blkfam_code "2")
    )
    ((= lib_blkfam "tu")
     (setq lib_blkfam_code "3")
    )
    ((= lib_blkfam "ic")
     (setq lib_blkfam_code "4")
    )
    ((= lib_blkfam "tl")
     (setq lib_blkfam_code "5")
    )
    ((= lib_blkfam "ac")
     (setq lib_blkfam_code "6")
    )
    ((= lib_blkfam "cc")
     (setq lib_blkfam_code "7")
    )
    ((= lib_blkfam "mt")
     (setq lib_blkfam_code "8")
    )
    ((= lib_blkfam "tp")
     (setq lib_blkfam_code "9")
    )
  )
  (set_tile "newlib_label" (strcat "Biblioteca de " (nth (fix (distof lib_blkfam_code)) lib_full_list)))
)


;ao selecionar uma família na DCL de Biblioteca (Professional)
(defun new_label_action ()
  (setq lib_blkfam_code $value)
  (cond
    ((= lib_blkfam_code "0") (setq lib_blkfam "sg"))
    ((= lib_blkfam_code "1") (setq lib_blkfam "aq"))
    ((= lib_blkfam_code "2") (setq lib_blkfam "el"))
    ((= lib_blkfam_code "3") (setq lib_blkfam "tu"))
    ((= lib_blkfam_code "4") (setq lib_blkfam "ic"))
    ((= lib_blkfam_code "5") (setq lib_blkfam "tl"))
    ((= lib_blkfam_code "6") (setq lib_blkfam "ac"))
    ((= lib_blkfam_code "7") (setq lib_blkfam "cc"))
    ((= lib_blkfam_code "8") (setq lib_blkfam "mt"))
    ((= lib_blkfam_code "9") (setq lib_blkfam "tp"))
  )
  (setq lib_blkgrp "00"
	lib_blksub "00"
	lib_blkpag "01"
	lib_blkblk "11"
  )
  (setq lib_blktog "0")
  (setq lib_inslay "0")
  (setq lib_explode "0")
  (lib_clearimg)
  (lib_dcl_action)
)


;distribuidor
(defun lib_cfgmain_lib ()
  (if (not (findfile (strcat cnp_root "/slides/" lib_blkpfx lib_blkfam lib_blkgrp lib_blksub lib_blkpag ".txt")))
    (progn
      (setq lib_blkgrp "00")
      (setq lib_blksub "00")
      (setq lib_blkpag "01")
      (setq lib_blkblk "11")
      (setq lib_blkscl "1.0")
    )
  )    
  (setq lib_blkfam_bkp lib_blkfam)
  (lib_dcl)
  (if (= lib_cfgmain_return 1) (lib_cfg_main))
)

;lê os dados iniciais da DCL no arquivo de dados
(defun lib_cfg_file ()
  (if (findfile (strcat cnp_root "/config/lastlib.txt"))
    (lib_lastlib_readfile)
    (progn
      (setq file (open (strcat cnp_root "/config/lastlib.txt") "w" "utf8"))
      (write-line "00" file)
      (write-line "00" file)
      (write-line "01" file)
      (write-line "11" file)
      (write-line "1.0" file)
      (close file)
      (lib_lastlib_readfile)
    )
  )
)

;função que lê o arquivo de dados
(defun lib_lastlib_readfile ()
  (if (= nil lib_blkgrp) (setq lib_blkgrp "00"))
  (if (= nil lib_blksub) (setq lib_blksub "00"))
  (if (= nil lib_blkpag) (setq lib_blkpag "01"))
  (if (= nil lib_blkblk) (setq lib_blkblk "11"))
  (if (= nil lib_blkscl) (setq lib_blkscl "1.0"))
)

;caixa de diálogo
(defun lib_dcl ()
  (setq lib_blktog "0")
  (setq lib_inslay "0")
  (setq lib_explode "0")
  ;abre a dcl
  (setq dcl_id (load_dialog (strcat cnp_root "/lisp/cadnorma.dcl")))
  (cond
    ((= lib_type "admin") (if (not (new_dialog "new_library4" dcl_id)) (exit)))
    ((= lib_type "user") (if (not (new_dialog "new_library3" dcl_id)) (exit)))
    ((= lib_type "fabr") (if (not (new_dialog "new_library5" dcl_id)) (exit)))
    ((= lib_type "fabr2") (if (not (new_dialog "new_library2" dcl_id)) (exit)))
  )
  
;;;  (if (= lib_type "admin")
;;;    (if (not (new_dialog "new_library4" dcl_id)) (exit))
;;;    (if (not (new_dialog "new_library3" dcl_id)) (exit))
;;;  )
  (lib_dcl_action)
;;;  (lib_label)
  (action_tile "lib_insert_curlay" "(setq lib_inslay $value)")
  (action_tile "lib_insert_explode" "(setq lib_explode $value)")
  (action_tile "lib_grplist" "(lib_action_grplist)")
  (action_tile "lib_sublist" "(lib_action_sublist)")
  (action_tile "lib_paglist" "(lib_action_paglist)")
  (action_tile "lib_blknext" "(lib_action_next)")
  (action_tile "lib_blkprev" "(lib_action_prev)")
  (action_tile "lib_blkredef" "(done_dialog 2)")
  (action_tile "lib_blkslide" "(done_dialog 3)")
  (action_tile "lib_blkclear" "(done_dialog 4)")
  (action_tile "lib_blkamplify" "(done_dialog 5)")
  (action_tile "lib_descr_altera" "(done_dialog 6)")
  (action_tile "lib_descr_insere" "(done_dialog 10)")
  (action_tile "lib_blkexchange" "(done_dialog 7)")
  (action_tile "lib_blkupdate" "(done_dialog 8)")
  (action_tile "lib_grpmng" "(done_dialog 9)")
  (action_tile "sub_chlayn" "(grp_sub_changenlay)")
  (action_tile "lib_blklaycol2" "(grp_sub_changecol)")
  (action_tile "lib_sclblk_toggle" "(setq lib_blktog $value)")
  (action_tile "lib_sclblk_factor" "(setq lib_blkscl $value)")
  (action_tile "icon11" "(lib_action_icon)")
  (action_tile "icon12" "(lib_action_icon)")
  (action_tile "icon13" "(lib_action_icon)")
  (action_tile "icon14" "(lib_action_icon)")
  (action_tile "icon21" "(lib_action_icon)")
  (action_tile "icon22" "(lib_action_icon)")
  (action_tile "icon23" "(lib_action_icon)")
  (action_tile "icon24" "(lib_action_icon)")
  (action_tile "icon31" "(lib_action_icon)")
  (action_tile "icon32" "(lib_action_icon)")
  (action_tile "icon33" "(lib_action_icon)")
  (action_tile "icon34" "(lib_action_icon)")
  (action_tile "icon41" "(lib_action_icon)")
  (action_tile "icon42" "(lib_action_icon)")
  (action_tile "icon43" "(lib_action_icon)")
  (action_tile "icon44" "(lib_action_icon)")
  (action_tile "lib_blkinsert" "(done_dialog 1)")
  (action_tile "lib_blkclose" "(done_dialog 0)")
  (action_tile "cancel" "(done_dialog 0)")
  (setq cn_lastlib_dialog (start_dialog))
  (unload_dialog dcl_id)
  ;o que fazer depois
;;;  (if (= 0 cn_lastlib_dialog) (lib_save_lastlib))
  (if (= 1 cn_lastlib_dialog) (lib_lastlib_insert))
  (if (= 2 cn_lastlib_dialog) (lib_action_redef))
  (if (= 3 cn_lastlib_dialog) (lib_action_slide))
  (if (= 4 cn_lastlib_dialog) (lib_action_clear))
  (if (= 5 cn_lastlib_dialog) (lib_action_amplify))
  (if (= 6 cn_lastlib_dialog) (lib_action_descript))
  (if (= 7 cn_lastlib_dialog) (lib_action_exchange))
  (if (= 8 cn_lastlib_dialog) (lib_action_blkupdate))
  (if (= 9 cn_lastlib_dialog) (lib_manager))
  (if (= 10 cn_lastlib_dialog) (lib_action_descript2))
)

(defun lib_dcl_action ()
  ;preenchimento da dcl
  (if (and (/= lib_type "fabr") (/= lib_type "fabr2")) (lib_label))
;;;  (lib_label)
  (lib_fillgrp)
  (lib_fillsub)
  (lib_fillpag)
  (lib_fillimg)
  (lib_fillgpp)
  (lib_fill_currpage)
  (lib_scaleblock)
  ;estados iniciais dos tiles
  (mode_tile "lib_blklaycol" 1)
  (mode_tile "lib_blkprev" 1)
  (mode_tile "lib_blknext" 1)
  (mode_tile "lib_descr_altera" 1)
  (mode_tile "lib_descr_insere" 1)
  (lib_blk_grayout)
  (set_tile "lib_grplist" (rtos (distof lib_blkgrp) 2 0))
  (set_tile "lib_sublist" (rtos (distof lib_blksub) 2 0))
  (set_tile "lib_sclblk_factor" lib_blkscl)
  (set_tile "lib_insert_curlay" "0")
  (lib_nextprev)
  ;ações das listas
)

;**************************************************
;função que escreve a descrição do bloco no desenho
;**************************************************
(defun lib_action_descript2 ()
;;;  (lib_save_lastlib)
  (setq n_descr (fix (distof lib_paglist_key))
	curr_descr (nth n_descr lib_paglist))
  (lib_action_descript3)
)

(defun lib_action_descript3 ()
  (setq psimb_txt nil pt1 nil)
  (lib_descr_readfile)
  (initget 128)
  (setq pt1 (getpoint "\nModel Space/Layout/Formatar texto/Editar Texto/<Ponto de inserção do texto...> "))
  (cond
    ((= 'LIST (type pt1))
     (setq psimb_txt pt1)
     (lib_descr_writext)
     )
    ((= 'STR  (type pt1))
     (cond
       ((= "F" (strcase pt1))
	(lib_descr_format)
	(lib_action_descript2))
       ((= "E" (strcase pt1))
	(lib_descr_modify))
       ((= "M" (strcase pt1))
	(command "._tilemode" "1")
	(lib_action_descript2))
       ((= "L" (strcase pt1))
	(command "._tilemode" "0" "._pspace")
	(lib_action_descript2))
       (t
	(prompt "\nOpção inválida! Digite F, E, M, L ou Clique no ponto de Inserção...")
	(lib_action_descript2))
      );cond
     )
   );cond
)

;modifica texto existente
(defun lib_descr_modify ()
  (prompt "\nSelecione um texto para receber a descrição... ")
  (setq ent2 (entsel)
	ent2_list (entget (car ent2))
	ent2_type (cdr (assoc 0 ent2_list)))
  (if (/= "TEXT" (strcase ent2_type))
    (progn
      (alert "Entidade não é um texto!")
      (lib_descr_modify)
    )
    (progn
      (entmod (setq ent2_list (subst (cons 1 curr_descr) (assoc 1 ent2_list) ent2_list)))
    )
  )
)
	


;escreve o texto da descrição
(defun lib_descr_writext ()
  (setq txdescr_stylist (list "r50" "r60" "r70" "r80" "r90" "r100" "r120" "r140" "r175" "r200"
			    "t1" "t2" "t3" "t4" "t5" "t6" "t7")
	blkdescr_style (nth (fix (distof blkdescr_sty)) txdescr_stylist)
  )
  (if (= "1" blkdescr_cxa) (setq curr_descr (strcase curr_descr)))
  (cn7_verylayer "Blocos_descrição" 2)  
  (cn7_txsimb blkdescr_style "bl" curr_descr (fix (distof blkdescr_col)) blkdescr_lay 0)
)


;formatação do texto de legenda
(defun lib_descr_format ()
  (setq dcl_id (load_dialog (strcat cnp_root "/lisp/cadnorma.dcl")))
  (if (not (new_dialog "cn9_descr_sty" dcl_id)) (exit))
  ;estilo do texto
  (setq txdescr_stylist (list "r50" "r60" "r70" "r80" "r90" "r100" "r120" "r140" "r175" "r200"
			    "t1" "t2" "t3" "t4" "t5" "t6" "t7"))
  (start_list "cn9_descr_style")
  (mapcar 'add_list txdescr_stylist)
  (end_list)
  (set_tile "cn9_descr_style" blkdescr_sty)
  (action_tile "cn9_descr_style" "(setq blkdescr_sty $value)")
  ;cor do texto
  (start_image "cn9_descr_color")
  (fill_image  0  0
    (dimx_tile "cn9_descr_color")
    (dimy_tile "cn9_descr_color")
    (fix (distof blkdescr_col))
  )
  (end_image)
  (action_tile "cn9_descr_color" "(cn9_descr_txcol)")
  ;layer de inserção
  (set_tile "cn9_descr_layer" blkdescr_lay)
  (action_tile "cn9_descr_layer" "(setq blkdescr_lay $value)")
  ;Escrever em maiúscula
  (set_tile "cn9_descr_cxa" blkdescr_cxa)
  (action_tile "cn9_descr_cxa" "(setq blkdescr_cxa $value)")
  ;ok_cancel
  (action_tile "cancel" "(done_dialog 0)")
  (action_tile "accept" "(done_dialog 1)")
  (setq lib_descr_dcl (start_dialog))
  (unload_dialog dcl_id)
  (if (= lib_descr_dcl 1) (lib_descr_writefile))
);defun


;define a cor do texto de descrição
;escolher cor do texto
(defun cn9_descr_txcol ()
  (setq cn9_descr_newcol (acad_colordlg (fix (distof blkdescr_col))))
  (if (/= nil cn9_descr_newcol) (setq blkdescr_col (rtos cn9_descr_newcol 2 0)))
  (start_image "cn9_descr_color")
  (fill_image  0  0
    (dimx_tile "cn9_descr_color")
    (dimy_tile "cn9_descr_color")
    (fix (distof blkdescr_col))
  )
  (end_image)
)
;escreve o arquivo de descrição
(defun lib_descr_writefile ()
  (setq file (open (strcat cnp_root "/config/blkdescr.txt") "w" "utf8"))
  (write-line blkdescr_sty file)
  (write-line blkdescr_col file)
  (write-line blkdescr_lay file)
  (write-line blkdescr_cxa file)
  (close file)
)

;lê o arquivo de descrição
(defun lib_descr_readfile ()
  (if (not (findfile (strcat cnp_root "/config/blkdescr.txt")))
    (progn
      (setq file (open (strcat cnp_root "/config/blkdescr.txt") "w" "utf8"))
      (write-line "3" file)
      (write-line "2" file)
      (write-line "Blocos_descrição" file)
      (write-line "1" file)
      (close file)
    )
  )
  ;procura o valor padrão
  (setq	file (open (strcat cnp_root "/config/blkdescr.txt") "r" "utf8"))
  (setq blkdescr_sty (read-line file))
  (setq blkdescr_col (read-line file))
  (setq blkdescr_lay (read-line file))
  (setq blkdescr_cxa (read-line file))
  (close file)
)


;**************************************************
;função que escreve a descrição do bloco no desenho
;**************************************************
(defun c:blkd ()
  (prompt "\nSelecione um bloco para escrever sua descrição... ")
  (setq ent (entsel)
	ent_list (entget (car ent))
	ent_type (cdr (assoc 0 ent_list)))
  (if (= "INSERT" (strcase ent_type))
    (progn
      (setq ent_blkname (cdr (assoc 2 ent_list)))
      (blkd_testnorma)
    )
  )
  (princ)
)

;define se é bloco do Cadnorma
(defun blkd_testnorma ();teste
  (setq counter nil)
  (if (and
	(= 14 (strlen ent_blkname))
	(findfile (strcat cnp_root "/slides/" (substr ent_blkname 1 12) ".txt"))
      )
    (progn
      (setq blkd_ordem (substr ent_blkname 13 2))
      (cond
	((= blkd_ordem "11") (setq counter 1))
	((= blkd_ordem "12") (setq counter 2))
	((= blkd_ordem "13") (setq counter 3))
	((= blkd_ordem "14") (setq counter 4))
	((= blkd_ordem "21") (setq counter 5))
	((= blkd_ordem "22") (setq counter 6))
	((= blkd_ordem "23") (setq counter 7))
	((= blkd_ordem "24") (setq counter 8))
	((= blkd_ordem "31") (setq counter 9))
	((= blkd_ordem "32") (setq counter 10))
	((= blkd_ordem "33") (setq counter 11))
	((= blkd_ordem "34") (setq counter 12))
	((= blkd_ordem "41") (setq counter 13))
	((= blkd_ordem "42") (setq counter 14))
	((= blkd_ordem "43") (setq counter 15))
	((= blkd_ordem "44") (setq counter 16))
    );cond
      (setq open_file (open (strcat cnp_root "/slides/" (substr ent_blkname 1 12) ".txt") "r" "utf8"))
      (repeat counter
	(setq blkd_descr (read-line open_file))
      )
      (close open_file)
      (cn7_alert_yes_no "Descrição do bloco:" blkd_descr "Deseja transcrever para o desenho?")
      (if (= alert_resp "yes")
	(progn
	  (setq curr_descr blkd_descr)
	  (lib_action_descript3)
	)
      );if
   );progn
   (alert "O bloco selecionado\nnão pertence à Biblioteca\ndo Cadnorma!"))
)


;preenche página atual / total de páginas
(defun lib_fill_currpage ()
  (lib_findpages)
  (set_tile "lib_current_page" (strcat "Pág.: " lib_blkpag " / " lib_numpaginas))
)

;encontrar o número de páginas de um subgrupo
(defun lib_findpages ()
  (setq lib_currpage 1)
  (lib_findpages_findnext)
  (while (findfile lib_nextpage_file)
      (setq lib_currpage (1+ lib_currpage))
      (lib_findpages_findnext)
  )
  (setq lib_numpaginas (rtos lib_currpage 2 0))
  (if (= 1 (strlen lib_numpaginas)) (setq lib_numpaginas (strcat "0" lib_numpaginas)))
)

;encontra o nome do próximo arquivo de página
(defun lib_findpages_findnext ()
  (setq	lib_nextpage (1+ lib_currpage)
	lib_nextpage_str (rtos lib_nextpage 2 0))
  (if (= 1 (strlen lib_nextpage_str)) (setq lib_nextpage_str (strcat "0" lib_nextpage_str)))
  (setq lib_nextpage_file (strcat cnp_root "/slides/" lib_blkpfx lib_blkfam lib_blkgrp lib_blksub lib_nextpage_str ".txt"))
)

;botão 'Conflitos'
(defun lib_action_blkupdate ()
;;;  (lib_save_lastlib)
  (setq dcl_id (load_dialog (strcat cnp_root "/lisp/cadnorma.dcl")))
  (if (not (new_dialog "lib_blk_update" dcl_id)) (exit))
  (set_tile "blk_updt_radio" "blk_updt_update")
  (setq lib_blkupdt_action "blk_updt_update")
  (action_tile "blk_updt_radio" "(setq lib_blkupdt_action $value)")
  (action_tile "accept" "(done_dialog 1)")
  (action_tile "cancel" "(done_dialog 0)")
  (setq lib_atualizar (start_dialog))
  (unload_dialog dcl_id)
  (if (= 1 lib_atualizar) (lib_updblk_update))
)


(defun lib_updblk_update ()
  (setq dwg_blk (strcat lib_blkpfx lib_blkfam lib_blkgrp lib_blksub lib_blkpag lib_blkblk))
  (setq dwg_blk_file (strcat cnp_root "/blocos/" dwg_blk ".dwg"))
  (if (not (tblsearch "block" dwg_blk))
    (alert "\nNao existem definições desse bloco no desenho...")
    (progn
      (setq counter 1)
      (find_next_temp)
      (command "._rename" "_b" dwg_blk curr_temp)
      (if (= lib_blkupdt_action "blk_updt_update")
	(progn
	  (command "._insert" dwg_blk_file "_non" "0,0" "" "" "")
	  (command "._explode" (entlast))
	  (command "._block" curr_temp "_y" "0,0" "_p" "")
	  (command "._rename" "_b" dwg_blk next_temp)
	  (command "._rename" "_b" curr_temp dwg_blk)
	  (command "._rename" "_b" next_temp curr_temp)
	  (cn7_alert_ok
	    "O Cadnorma renomeou o bloco antigo para"
	    curr_temp
	    "Use o comando <PURGE> para eliminá-lo...")
        );progn case T
	(progn
	  (cn7_alert_ok
	    "O Cadnorma renomeou o bloco antigo para"
	    curr_temp
	    "Insira normalmente o novo bloco...")
	  (lib_dcl)
	);progn case F
      );if
    );progn
  );if
);defun

(defun find_next_temp ()
  (setq curr_temp (strcat "Renomeado_" (rtos counter 2 0)))
  (if (tblsearch "block" curr_temp)
    (progn
      (setq counter (1+ counter))
      (find_next_temp)
    );progn
    (setq next_temp (strcat "Renomeado_" (rtos (1+ counter) 2 0)))
  );if
);defun


  
;botão 'Substituir'
(defun lib_action_exchange ()
;;;  (lib_save_lastlib)
  (if (not (findfile lib_currdwg))
    (progn
      (cn7_alert_ok
	"Impossível operar substituição"
	"de blocos com ícones vazios!"
	"Selecione um ícone ocupado...")
      (lib_dcl)
    )
    (progn
      (prompt "\nSelecione um dos blocos que deseja substituir... ")
      (setq lib_blkproto (entsel)
	    lib_blkproto_type (cdr (assoc 0 (entget (car lib_blkproto)))))
      (if (/= "INSERT" lib_blkproto_type)
	(progn
	  (alert "Objeto selecionado\nnão é um bloco!\nTente novamente...")
	  (lib_action_exchange)
	  )
	(progn
	  (setq lib_blkproto_list (entget (car lib_blkproto))
		lib_blkproto_name (cdr (assoc 2 lib_blkproto_list))
		lib_blkproto_xscl (cdr (assoc 41 lib_blkproto_list))
;;;		lib_blkproto_yscl (cdr (assoc 42 lib_blkproto_list))
;;;		lib_blkproto_zscl (cdr (assoc 43 lib_blkproto_list))
	  )
	  (prompt "Selecione os objetos ou área para substituir os blocos...<ENTER> para anterior... ")
	  (setq exchange_sel (ssget '((0 . "INSERT"))))
	  (if (= nil exchange_sel)
	    (progn
	      (setq exchange_sel (ssadd))
	      (setq exchange_sel (ssadd (car lib_blkproto) exchange_sel))
	    )
	  )
	  (setq exchange_sel_n (sslength exchange_sel)
		counter 0)
	  (repeat exchange_sel_n
	    (setq entname (ssname exchange_sel counter)
		  ent_blkname (cdr (assoc 2 (entget entname)))
		  ent_insert (cdr (assoc 10 (entget entname)))
		  ent_scale (cdr (assoc 41 (entget entname)))
		  ent_rotation (cdr (assoc 50 (entget entname)))
		  angdeg (/ (* 180 ent_rotation) pi))
	    (if (= lib_blkproto_name ent_blkname)
	      (progn
		(command "._erase" entname "")
		(cn7_find_blkscl);***
		(setq pt1 ent_insert);(cn7_insert_point);***
		(cn7_verylayer (strcat cn7_blk_prefixlay lib_currsgp_layname) (fix (distof lib_currsgp_laycol)));***
		(command "._insert" lib_currdwg "_scale" ent_scale ;|cn7_blkscl|; "_non" pt1 angdeg);***
		)
	      )
	    (setq counter (1+ counter))
	    )
	  )
	)
    )
  )
)

;botão 'Descrição'
(defun lib_action_descript ()
;;;  (lib_save_lastlib)
  (setq dcl_id (load_dialog (strcat cnp_root "/lisp/cadnorma.dcl")))
  (if (not (new_dialog "cn7_red_descript" dcl_id)) (exit))
  (setq n_descr (fix (distof lib_paglist_key))
	curr_descr (nth n_descr lib_paglist))
  (set_tile "cn7_chg_descript" curr_descr)
  (mode_tile "cn7_chg_descript" 2)
  (action_tile "cn7_chg_descript" "(setq cn7_new_descr $value)")
  (action_tile "accept" "(done_dialog 1)")
  (action_tile "cancel" "(done_dialog 0)")
  (setq chg_descr (start_dialog))
  (unload_dialog dcl_id)
  (if (= chg_descr 1) (progn (lib_chg_descript) (lib_dcl)))
)


;atualiza o arquivo de descrições da página
(defun lib_chg_descript ()
  (setq counter 0 lib_newpaglist (list))
  (repeat 16
    (if (= counter n_descr)
      (setq lib_newpaglist (append lib_newpaglist (list cn7_new_descr)))
      (setq lib_newpaglist (append lib_newpaglist (list (nth counter lib_paglist))))
    )
    (setq counter (1+ counter))
    (setq open_file (open (strcat cnp_root "/slides/" lib_blkpfx lib_blkfam lib_blkgrp lib_blksub lib_blkpag ".txt") "w" "utf8"))
    (foreach n lib_newpaglist
      (write-line n open_file)
    )
    (close open_file)
  )
)


;botão ampliar
(defun lib_action_amplify ()
;;;  (lib_save_lastlib)
  (setq dcl_id2 (load_dialog (strcat cnp_root "/lisp/cadnorma.dcl")))
  (if (not (new_dialog "lib_amplify" dcl_id2)) (exit))
  (setq x (dimx_tile "sld_amplify")
	y (dimy_tile "sld_amplify"))
  (start_image "sld_amplify")
  (slide_image 0 0 x y curr_icon);curr_icon
  (end_image)
  (setq n_descr (fix (distof lib_paglist_key))
	curr_descr (nth n_descr lib_paglist))
  (set_tile "lib_amplify_descript" curr_descr)
  (action_tile "lib_amplify_insert" "(done_dialog 2)")
  (action_tile "accept" "(done_dialog 1)")
  (action_tile "cancel" "(done_dialog 0)")
  (setq lib_amp (start_dialog))
  (unload_dialog dcl_id2)
  (if (= 0 lib_amp) (lib_dcl))
  (if (= 1 lib_amp) (lib_dcl))
  (if (= 2 lib_amp) (lib_lastlib_insert))
)

;botão Limpar
(defun lib_action_clear () (cnp:unsupported "lib_action_clear"))

;troca / por \\ no nome do arquivo
(defun transf_dwg_name ()
  (setq n (strlen lib_currdwg) count 1 new_dwg "")
  (repeat n
    (if (= (substr lib_currdwg count 1) "/")
      (setq new_dwg (strcat new_dwg "\\"))
      (setq new_dwg (strcat new_dwg (substr lib_currdwg count 1)))
      );if
    (setq count (1+ count))
  );repeat
);defun

;troca / por \\ no nome do slide
(defun transf_sld_name ()
  (setq n (strlen lib_currsld) count 1 new_sld "")
  (repeat n
    (if (= (substr lib_currsld count 1) "/")
      (setq new_sld (strcat new_sld "\\"))
      (setq new_sld (strcat new_sld (substr lib_currsld count 1)))
      );if
    (setq count (1+ count))
  );repeat
);defun


;botão Slide
(defun lib_action_slide () (cnp:unsupported "lib_action_slide"))


;botão Redefinir
(defun lib_action_redef () (cnp:unsupported "lib_action_redef"))

;cria o arquivo de slides a serem gerados
(defun lib_writeslb ()
  (setq open_file (open (strcat cnp_root "/slides/cadnslides.txt") "w" "utf8"))
  (write-line (strcat cnp_root "/slides/" lib_blkpfx lib_blkfam lib_blkgrp lib_blksub lib_blkpag "11") open_file)
  (write-line (strcat cnp_root "/slides/" lib_blkpfx lib_blkfam lib_blkgrp lib_blksub lib_blkpag "12") open_file)
  (write-line (strcat cnp_root "/slides/" lib_blkpfx lib_blkfam lib_blkgrp lib_blksub lib_blkpag "13") open_file)
  (write-line (strcat cnp_root "/slides/" lib_blkpfx lib_blkfam lib_blkgrp lib_blksub lib_blkpag "14") open_file)
  (write-line (strcat cnp_root "/slides/" lib_blkpfx lib_blkfam lib_blkgrp lib_blksub lib_blkpag "21") open_file)
  (write-line (strcat cnp_root "/slides/" lib_blkpfx lib_blkfam lib_blkgrp lib_blksub lib_blkpag "22") open_file)
  (write-line (strcat cnp_root "/slides/" lib_blkpfx lib_blkfam lib_blkgrp lib_blksub lib_blkpag "23") open_file)
  (write-line (strcat cnp_root "/slides/" lib_blkpfx lib_blkfam lib_blkgrp lib_blksub lib_blkpag "24") open_file)
  (write-line (strcat cnp_root "/slides/" lib_blkpfx lib_blkfam lib_blkgrp lib_blksub lib_blkpag "31") open_file)
  (write-line (strcat cnp_root "/slides/" lib_blkpfx lib_blkfam lib_blkgrp lib_blksub lib_blkpag "32") open_file)
  (write-line (strcat cnp_root "/slides/" lib_blkpfx lib_blkfam lib_blkgrp lib_blksub lib_blkpag "33") open_file)
  (write-line (strcat cnp_root "/slides/" lib_blkpfx lib_blkfam lib_blkgrp lib_blksub lib_blkpag "34") open_file)
  (write-line (strcat cnp_root "/slides/" lib_blkpfx lib_blkfam lib_blkgrp lib_blksub lib_blkpag "41") open_file)
  (write-line (strcat cnp_root "/slides/" lib_blkpfx lib_blkfam lib_blkgrp lib_blksub lib_blkpag "42") open_file)
  (write-line (strcat cnp_root "/slides/" lib_blkpfx lib_blkfam lib_blkgrp lib_blksub lib_blkpag "43") open_file)
  (write-line (strcat cnp_root "/slides/" lib_blkpfx lib_blkfam lib_blkgrp lib_blksub lib_blkpag "44") open_file)
  (close open_file)
)
  
;botão próxima
(defun lib_action_next ()
  (setq lib_blkpag next_page_str)
  (lib_clearimg)
  (lib_fillimg)
  (lib_fillpag)
  (lib_nextprev)
  (lib_fill_currpage)
)

;botão anterior
(defun lib_action_prev ()
  (setq lib_blkpag prev_page_str)
  (lib_clearimg)
  (lib_fillimg)
  (lib_fillpag)
  (lib_nextprev)
  (lib_fill_currpage)
)

;verifica se existe próxima e anterior
(defun lib_nextprev ()
  (setq curr_page (fix (distof lib_blkpag))
	next_page (1+ curr_page)
	next_page_str (rtos next_page 2 0)
	prev_page (1- curr_page)
	prev_page_str (rtos prev_page 2 0))
  (if (= 1 (strlen next_page_str)) (setq next_page_str (strcat "0" next_page_str)))
  (if (= 1 (strlen prev_page_str)) (setq prev_page_str (strcat "0" prev_page_str)))
  (setq next_page_file (strcat cnp_root "/slides/" lib_blkpfx lib_blkfam lib_blkgrp lib_blksub next_page_str ".txt")
	prev_page_file (strcat cnp_root "/slides/" lib_blkpfx lib_blkfam lib_blkgrp lib_blksub prev_page_str ".txt")
  )
  (if (findfile next_page_file) (mode_tile "lib_blknext" 0) (mode_tile "lib_blknext" 1))
  (if (findfile prev_page_file) (mode_tile "lib_blkprev" 0) (mode_tile "lib_blkprev" 1))
)

;grayout nos botões de bloco selecionado
(defun lib_blk_grayout ()
  (mode_tile "lib_blkredef" 1)
  (mode_tile "lib_blkslide" 1)
  (mode_tile "lib_blkclear" 1)
  (mode_tile "lib_blkamplify" 1)
  (mode_tile "lib_blkupdate" 1)
  (mode_tile "lib_blkinsert" 1)
  (mode_tile "lib_descr_altera" 1)
  (mode_tile "lib_descr_escreve" 1)
  (mode_tile "lib_blkexchange" 1)
)

;grayout nos botões de bloco selecionado
(defun lib_blk_grayin ()
  (mode_tile "lib_blkredef" 0)
  (mode_tile "lib_blkslide" 0)
  (mode_tile "lib_blkclear" 0)
  (mode_tile "lib_blkamplify" 0)
  (mode_tile "lib_blkupdate" 0)
  (mode_tile "lib_blkinsert" 0)
  (mode_tile "lib_descr_altera" 0)
  (mode_tile "lib_descr_insere" 0)
  (mode_tile "lib_blkexchange" 0)
)

  
;ao selecionar um icon:
;	acende o item correspondente na listagem
(defun lib_action_icon ()
  (lib_blk_grayin)
  (setq lib_blkblk (substr $key 5 2))
  (cond
    ((= lib_blkblk "11") (setq lib_paglist_key "00") (set_tile "lib_paglist" "0"))
    ((= lib_blkblk "12") (setq lib_paglist_key "01") (set_tile "lib_paglist" "1"))
    ((= lib_blkblk "13") (setq lib_paglist_key "02") (set_tile "lib_paglist" "2"))
    ((= lib_blkblk "14") (setq lib_paglist_key "03") (set_tile "lib_paglist" "3"))
    ((= lib_blkblk "21") (setq lib_paglist_key "04") (set_tile "lib_paglist" "4"))
    ((= lib_blkblk "22") (setq lib_paglist_key "05") (set_tile "lib_paglist" "5"))
    ((= lib_blkblk "23") (setq lib_paglist_key "06") (set_tile "lib_paglist" "6"))
    ((= lib_blkblk "24") (setq lib_paglist_key "07") (set_tile "lib_paglist" "7"))
    ((= lib_blkblk "31") (setq lib_paglist_key "08") (set_tile "lib_paglist" "8"))
    ((= lib_blkblk "32") (setq lib_paglist_key "09") (set_tile "lib_paglist" "9"))
    ((= lib_blkblk "33") (setq lib_paglist_key "10") (set_tile "lib_paglist" "10"))
    ((= lib_blkblk "34") (setq lib_paglist_key "11") (set_tile "lib_paglist" "11"))
    ((= lib_blkblk "41") (setq lib_paglist_key "12") (set_tile "lib_paglist" "12"))
    ((= lib_blkblk "42") (setq lib_paglist_key "13") (set_tile "lib_paglist" "13"))
    ((= lib_blkblk "43") (setq lib_paglist_key "14") (set_tile "lib_paglist" "14"))
    ((= lib_blkblk "44") (setq lib_paglist_key "15") (set_tile "lib_paglist" "15"))
  )
  (lib_blkfiles)
)


;ao selecionar um bloco da lista:
;	acende o icon correspondente
;
(defun lib_action_paglist ()
  (lib_blk_grayin)
  (setq lib_paglist_key $value)
  (if (= 1 (strlen lib_paglist_key)) (setq lib_paglist_key (strcat "0" lib_paglist_key)))
  (cond
    ((= lib_paglist_key "00") (setq lib_blkblk "11") (mode_tile "icon11" 2))
    ((= lib_paglist_key "01") (setq lib_blkblk "12") (mode_tile "icon12" 2))
    ((= lib_paglist_key "02") (setq lib_blkblk "13") (mode_tile "icon13" 2))
    ((= lib_paglist_key "03") (setq lib_blkblk "14") (mode_tile "icon14" 2))
    ((= lib_paglist_key "04") (setq lib_blkblk "21") (mode_tile "icon21" 2))
    ((= lib_paglist_key "05") (setq lib_blkblk "22") (mode_tile "icon22" 2))
    ((= lib_paglist_key "06") (setq lib_blkblk "23") (mode_tile "icon23" 2))
    ((= lib_paglist_key "07") (setq lib_blkblk "24") (mode_tile "icon24" 2))
    ((= lib_paglist_key "08") (setq lib_blkblk "31") (mode_tile "icon31" 2))
    ((= lib_paglist_key "09") (setq lib_blkblk "32") (mode_tile "icon32" 2))
    ((= lib_paglist_key "10") (setq lib_blkblk "33") (mode_tile "icon33" 2))
    ((= lib_paglist_key "11") (setq lib_blkblk "34") (mode_tile "icon34" 2))
    ((= lib_paglist_key "12") (setq lib_blkblk "41") (mode_tile "icon41" 2))
    ((= lib_paglist_key "13") (setq lib_blkblk "42") (mode_tile "icon42" 2))
    ((= lib_paglist_key "14") (setq lib_blkblk "43") (mode_tile "icon43" 2))
    ((= lib_paglist_key "15") (setq lib_blkblk "44") (mode_tile "icon44" 2))
  )
  (lib_blkfiles)
)

;rotina chave:define os arquivos relacionados a um bloco
(defun lib_blkfiles ()
  (setq lib_currdwg (strcat cnp_root "/blocos/" lib_blkpfx lib_blkfam lib_blkgrp lib_blksub lib_blkpag lib_blkblk ".dwg")
	lib_currsld (strcat cnp_root "/slides/" lib_blkpfx lib_blkfam lib_blkgrp lib_blksub lib_blkpag lib_blkblk ".sld")
	lib_currslb (strcat cnp_root "/slides/" lib_blkpfx lib_blkfam lib_blkgrp lib_blksub lib_blkpag)
	curr_icon (strcat cnp_root "/slides/" lib_blkpfx lib_blkfam lib_blkgrp lib_blksub lib_blkpag
			  "("  lib_blkpfx lib_blkfam lib_blkgrp lib_blksub lib_blkpag lib_blkblk ")")
  )
)


;ao selecionar um subgrupo:
;	atualiza a lista de blocos
;	atualiza os slides
;	atualiza as propiedades
(defun lib_action_sublist ()
  (lib_blk_grayout)
  (setq lib_sublist_key $value
	lib_blkpag "01")
  (if (= 1 (strlen lib_sublist_key)) (setq lib_sublist_key (strcat "0" lib_sublist_key)))
  (setq lib_blksub lib_sublist_key)
  (lib_clearimg)
  (lib_fillimg)
  (lib_fillpag)
  (lib_fillgpp)
  (lib_nextprev)
  (lib_fill_currpage)
  (lib_scaleblock)
)

;controla escala de inserção de blocos gráficos
(defun lib_scaleblock ()
  (if (= "1" grp_type)
    (progn
      (mode_tile "lib_sclblk_toggle" 1)
      (mode_tile "lib_sclblk_factor" 1)
    )
    (progn
      (mode_tile "lib_sclblk_toggle" 0)
      (mode_tile "lib_sclblk_factor" 0)
    )
  )
)

(defun lib_fillgpp ()
  (setq lib_currsgp (strcat cnp_root "/slides/" lib_blkpfx lib_blkfam lib_blkgrp lib_blksub ".sgp")
	lib_currsgp_open (open lib_currsgp "r" "utf8")
	grp_type (read-line lib_currsgp_open)
	grp_unit (read-line lib_currsgp_open)
	lib_currsgp_layname (read-line lib_currsgp_open)
	lib_currsgp_laycol (read-line lib_currsgp_open))
  (close lib_currsgp_open)
  (if (= "1" grp_type)
    (setq txpart1 "Tipo = Real ; ")
    (setq txpart1 "Tipo = Gráfico ; ")
  )
  (cond
    ((= "1" grp_unit) (setq txpart2 "Unid. = Metro"))
    ((= "100" grp_unit) (setq txpart2 "Unid. = Centímetro"))
    ((= "1000" grp_unit) (setq txpart2 "Unid. = Milímetro"))
  )
  (set_tile "lib_blktype" (strcat txpart1 txpart2))
  (set_tile "lib_blklayer" (strcat "Layer = " lib_currsgp_layname))
  (start_image "lib_blklaycol")
  (fill_image  0  0
    (dimx_tile "lib_blklaycol")
    (dimy_tile "lib_blklaycol")
    (fix (distof lib_currsgp_laycol))
  )
  (end_image)
)

;ao selecionar um grupo, preenche o subgrupo
(defun lib_action_grplist ()
  (setq lib_grplist_key $value)
  (if (= 1 (strlen lib_grplist_key)) (setq lib_grplist_key (strcat "0" lib_grplist_key)))
  (setq lib_blkgrp lib_grplist_key
	lib_blksub "00"
	lib_blkpag "01"
	lib_blkblk "11")
  (lib_fillsub)
  (set_tile "lib_sublist" "0")
  (lib_clearimg)
  (lib_fillimg)
  (lib_fillgpp)
  (lib_fillpag)
  (lib_fill_currpage)
  (lib_nextprev)
)

;***************************************************
;botão "Inserir"
;salva o arquivo e insere o bloco
;***************************************************
(defun lib_lastlib_insert ()
;;;  (lib_save_lastlib)
  (if (not (findfile lib_currdwg))
    (progn
      (cn7_alert_ok 
	"Bloco não encontrado,"
	"ou arquivo corrompido!"
	"Selecione outro ícone...")	
      (lib_dcl)
    )
    (progn
      (cn7_find_blkscl)
      ;(cn7_insert_point)
      (if (= lib_inslay "0")
	(cn7_verylayer (strcat cn7_blk_prefixlay lib_currsgp_layname) (fix (distof lib_currsgp_laycol)))
      )
      (if (= lib_blktog "1") (setq cn7_blkscl (* cn7_blkscl (distof lib_blkscl))))
      (prompt "\nSelecione o ponto de inserção e escolha o ângulo de rotação... ")
      (command "._insert" lib_currdwg "_scale" cn7_blkscl)
    )
  )
)

(defun c:ru ()
  (if (not (findfile lib_currdwg))
    (progn
      (cn7_alert_ok 
	"Bloco não encontrado,"
	"ou arquivo corrompido!"
	"Selecione outro ícone...")	
      (lib_dcl)
    )
    (progn
      (cn7_find_blkscl)
      ;(cn7_insert_point)
      (if (= lib_inslay "0")
	(cn7_verylayer (strcat cn7_blk_prefixlay lib_currsgp_layname) (fix (distof lib_currsgp_laycol)))
      )
      (if (= lib_blktog "1") (setq cn7_blkscl (* cn7_blkscl (distof lib_blkscl))))
      (prompt "\nSelecione o ponto de inserção e escolha o ângulo de rotação... ")
      (command "._insert" lib_currdwg "_scale" cn7_blkscl pause pause)
    )
  )
  (princ)
)
  

(defun cn7_insert_point ()
  (initget 128)
  (setq pt1 (getpoint "\nMeio de 2 pontos/<Ponto de inserção...>"))
  (cond
    ((= 'LIST (type pt1))
     (setq pt1 pt1)
     )
    ((= 'STR  (type pt1))
     (cond
       ((or (= "M" (strcase pt1)) (= "2" (strcase pt1)))
	(setq pt2 (getpoint "\nPrimeiro ponto, de dois...")
	      pt3 (getpoint pt2 "\nSegundo ponto, de dois...")
	      pt1 (polar pt2 (angle pt2 pt3) (/ (distance pt2 pt3) 2)))
	)
       (t (prompt "\nOpção inválida! Digite 'M' ou marque o primeiro ponto...")
	(cn7_insert_point)
	)
       )
     )
    )
  )





;limpa os slides
(defun lib_clearimg ()
  (setq kl "11") (lib_upd_icon2)
  (setq kl "12") (lib_upd_icon2)
  (setq kl "13") (lib_upd_icon2)
  (setq kl "14") (lib_upd_icon2)
  (setq kl "21") (lib_upd_icon2)
  (setq kl "22") (lib_upd_icon2)
  (setq kl "23") (lib_upd_icon2)
  (setq kl "24") (lib_upd_icon2)
  (setq kl "31") (lib_upd_icon2)
  (setq kl "32") (lib_upd_icon2)
  (setq kl "33") (lib_upd_icon2)
  (setq kl "34") (lib_upd_icon2)
  (setq kl "41") (lib_upd_icon2)
  (setq kl "42") (lib_upd_icon2)
  (setq kl "43") (lib_upd_icon2)
  (setq kl "44") (lib_upd_icon2)
)

(defun lib_upd_icon2 ()
  (setq x (dimx_tile (strcat "icon" kl)) y (dimy_tile (strcat "icon" kl)))
  (start_image (strcat "icon" kl))
  (fill_image 0 0 x y -2)
  (end_image)
)

;preenche os slides
(defun lib_fillimg ()
   (setq kl "11") (lib_upd_icon)
   (setq kl "12") (lib_upd_icon)
   (setq kl "13") (lib_upd_icon)
   (setq kl "14") (lib_upd_icon)
   (setq kl "21") (lib_upd_icon)
   (setq kl "22") (lib_upd_icon)
   (setq kl "23") (lib_upd_icon)
   (setq kl "24") (lib_upd_icon)
   (setq kl "31") (lib_upd_icon)
   (setq kl "32") (lib_upd_icon)
   (setq kl "33") (lib_upd_icon)
   (setq kl "34") (lib_upd_icon)
   (setq kl "41") (lib_upd_icon)
   (setq kl "42") (lib_upd_icon)
   (setq kl "43") (lib_upd_icon)
   (setq kl "44") (lib_upd_icon)
)

(defun lib_upd_icon ()
   (setq curr_icon (strcat cnp_root "/slides/" lib_blkpfx lib_blkfam lib_blkgrp lib_blksub lib_blkpag
			   "("  lib_blkpfx lib_blkfam lib_blkgrp lib_blksub lib_blkpag kl ")"))
   (setq x (dimx_tile (strcat "icon" kl)) y (dimy_tile (strcat "icon" kl)))
   (start_image (strcat "icon" kl))
   (slide_image 0 0 x y curr_icon)
   (end_image)
)


;preenche a listagem de grupos (último utilizado)
(defun lib_fillgrp ()
  (setq lib_grplist (list))
  (setq open_file (open (strcat cnp_root "/slides/" lib_blkpfx lib_blkfam ".txt") "r" "utf8"))
  ;cada linha contém nome;prefixo do grupo
  (while (/= nil (setq linha (read-line open_file)))
    (setq lib_grplist (append lib_grplist (list linha)))
  )
  (close open_file)
  (start_list "lib_grplist")
  (mapcar 'add_list lib_grplist)
  (end_list)
)

;preenche a listagem de sub-grupos (último utilizado)
(defun lib_fillsub ()
  (setq lib_sublist (list))
  (setq open_file (open (strcat cnp_root "/slides/" lib_blkpfx lib_blkfam lib_blkgrp ".txt") "r" "utf8"))
  (while (/= nil (setq linha (read-line open_file)))
    (setq lib_sublist (append lib_sublist (list linha)))
  )
  (close open_file)
  (start_list "lib_sublist")
  (mapcar 'add_list lib_sublist)
  (end_list)
)

;preenche a listagem de página (última utilizado)
(defun lib_fillpag ()
  (setq lib_paglist (list))
  (setq open_file (open (strcat cnp_root "/slides/" lib_blkpfx lib_blkfam lib_blkgrp lib_blksub lib_blkpag ".txt") "r" "utf8"))
  (while (/= nil (setq linha (read-line open_file)))
    (setq lib_paglist (append lib_paglist (list linha)))
  )
  (close open_file)
  (start_list "lib_paglist")
  (mapcar 'add_list lib_paglist)
  (end_list)
)

;guarda os valores da última biblioteca acessada
(defun lib_save_lastlib ()
  (setq file2 (open (strcat cnp_root "/config/lastlib.txt") "w" "utf8"))
  (write-line lib_blkgrp file2)
  (write-line lib_blksub file2)
  (write-line lib_blkpag file2)
  (write-line lib_blkblk file2)
  (write-line lib_blkscl file2)
  (close file2)
)

;***************************************************************
;	Gerenciador de Grupos					
;***************************************************************
(defun c:grp ()
  (if (not lib_blkfam) (setq lib_blkfam "aq"))
  (lib_manager)
  (princ)
)


;deniog
;abre e gerencia DCL
(defun lib_manager ()
  (setq dcl_id (load_dialog (strcat cnp_root "/lisp/cadnorma.dcl")))
  (if (not (new_dialog "lib_grpmanager" dcl_id)) (exit))
  (if (and (/= lib_type "fabr") (/= lib_type "fabr2")) (lib_mng_label))
  (lib_fillgrp)
  (lib_fillsub)
  (grp_buttons_off)
  (action_tile "lib_grplist" "(grp_grplist_action)")
  (action_tile "lib_sublist" "(grp_sublist_action)")
  (action_tile "sub_chtype" "(grp_sub_changetype)")
  (action_tile "sub_chunit" "(grp_sub_changeunit)")
  (action_tile "sub_chlayn" "(grp_sub_changenlay)")
  (action_tile "grp_sub_rename" "(grp_sub_rename)")
  (action_tile "cancel" "(done_dialog 0)")
  (action_tile "accept" "(done_dialog 1)")
  (action_tile "grp_grprename" "(done_dialog 2)")
  (action_tile "grp_grpnew" "(done_dialog 3)")
  (action_tile "grp_sub_page" "(done_dialog 4)")
  (action_tile "grp_sub_new" "(done_dialog 5)")
  (setq grpdcl_dialog (start_dialog))
  (unload_dialog dcl_id)
  (if (= 1 grpdcl_dialog) (lib_cfgmain_lib))
  (if (= 2 grpdcl_dialog) (grp_grprename_action))
  (if (= 3 grpdcl_dialog) (grp_grpnew_action))
  (if (= 4 grpdcl_dialog) (grp_grpmore_action))
  (if (= 5 grpdcl_dialog) (grp_grpnewsub_action))
)



;criar novo subgrupo
(defun grp_grpnewsub_action () (cnp:unsupported "grp_grpnewsub_action"))


      
;aumentar capacidade do subgrupo (criar nova página)
(defun grp_grpmore_action () (cnp:unsupported "grp_grpmore_action"))

;renomear subgrupo
(defun grp_sub_rename ()
  (setq sgp_chsubname_newname nil)
  (setq dcl_id (load_dialog (strcat cnp_root "/lisp/cadnorma.dcl")))
  (if (not (new_dialog "grp_sub_rename" dcl_id)) (exit))
  (set_tile "sub_chsubname_edit" (nth (read lib_blksub) lib_sublist))
  (mode_tile "sub_chsubname_edit" 2)
  (action_tile "sub_chsubname_edit" "(setq sgp_chsubname_newname $value)")
  (action_tile "cancel" "(done_dialog 0)")
  (action_tile "accept" "(done_dialog 1)")
  (setq sub_rename_dialog (start_dialog))
  (unload_dialog dcl_id)
  (if (= 1 sub_rename_dialog)
    (if (and (/= nil sgp_chsubname_newname) (/= "" sgp_chsubname_newname))
      (progn
	(setq n_ordem (read lib_blksub)
	      list_n (length lib_sublist)
	      counter 0
	      new_list (list "")
	)
	(repeat list_n
	  (if (= counter n_ordem)
	    (setq new_list (append new_list (list sgp_chsubname_newname)))
	    (setq new_list (append new_list (list (nth counter lib_sublist))))
	  )
	  (setq counter (1+ counter))
	);repeat
	(setq lib_sublist (cdr new_list))
	(setq open_file (open (strcat cnp_root "/slides/" lib_blkpfx lib_blkfam lib_blkgrp ".txt") "w" "utf8"))
	(foreach n lib_sublist
	  (write-line n open_file)
	)
	(close open_file)
	(lib_fillsub)
	(start_list "lib_sublist")
	(mapcar 'add_list lib_sublist)
	(end_list)
	(grp_buttons_off)
      )
    )
  )	      
)

;altera o layer de inserção do bloco
(defun grp_sub_changenlay ()
  (grp_sub_readprop)
  (setq sgp_chlayer_newlayer nil)
  (setq dcl_id (load_dialog (strcat cnp_root "/lisp/cadnorma.dcl")))
  (if (not (new_dialog "grp_sub_change_layer" dcl_id)) (exit))
  (set_tile "sub_chlayer_edit" sgp_sublayn)
  (action_tile "sub_chlayer_edit" "(setq sgp_chlayer_newlayer $value)")
  (mode_tile "sub_chlayer_edit" 2)
  (action_tile "cancel" "(done_dialog 0)")
  (action_tile "accept" "(done_dialog 1)")
  (setq sub_changelayer_dialog (start_dialog))
  (unload_dialog dcl_id)
  (if (= 1 sub_changelayer_dialog)
    (if (and (/= nil sgp_chlayer_newlayer) (/= "" sgp_chlayer_newlayer))
      (progn
	(setq sgp_sublayn sgp_chlayer_newlayer)
	(set_tile "lib_blklayer" sgp_chlayer_newlayer)
	(grp_sgp_resave)
      )
    )
  )
)

;altera a unidade do bloco
(defun grp_sub_changeunit ()
  (setq sgp_chunit_newunit nil)
  (setq dcl_id (load_dialog (strcat cnp_root "/lisp/cadnorma.dcl")))
  (if (not (new_dialog "grp_sub_change_unit" dcl_id)) (exit))
  (cond
    ((= sgp_subunit "1") (set_tile "sgp_chunit_radio" "sub_chunit_0"))
    ((= sgp_subunit "100") (set_tile "sgp_chunit_radio" "sub_chunit_1"))
    ((= sgp_subunit "1000") (set_tile "sgp_chunit_radio" "sub_chunit_2"))
  )
  (action_tile "sgp_chunit_radio" "(setq sgp_chunit_newunit $value)")
  (action_tile "accept" "(done_dialog 1)")
  (action_tile "cancel" "(done_dialog 0)")
  (setq sub_changeunit_dialog (start_dialog))
  (unload_dialog dcl_id)
  (if (= 1 sub_changeunit_dialog);se clica em 'ok' 
    (progn
      (if (/= nil sgp_chunit_newunit);se algum tipo foi clicado
	(progn
	  (cond
	    ((= sgp_chunit_newunit "sub_chunit_0") (setq sgp_subunit "1") (set_tile "lib_blkunit" "Unidade: Metros"))
	    ((= sgp_chunit_newunit "sub_chunit_1") (setq sgp_subunit "100") (set_tile "lib_blkunit" "Unidade: Centímetros"))
	    ((= sgp_chunit_newunit "sub_chunit_2") (setq sgp_subunit "1000") (set_tile "lib_blkunit" "Unidade: Milímetros"))
	  )	  	    
	  (grp_sgp_resave)
	)
      )
    )
  )
)

;altera o tipo de subgrupo
(defun grp_sub_changetype ()
  (setq sgp_chtype_newtype nil)
  (setq dcl_id (load_dialog (strcat cnp_root "/lisp/cadnorma.dcl")))
  (if (not (new_dialog "grp_sub_change_type" dcl_id)) (exit))
  (if (= sgp_subtype "1")
    (set_tile "sgp_chtype_radio" "sub_chtype_1")
    (set_tile "sgp_chtype_radio" "sub_chtype_2")
  )
  (action_tile "sgp_chtype_radio" "(setq sgp_chtype_newtype $value)")
  (action_tile "accept" "(done_dialog 1)")
  (action_tile "cancel" "(done_dialog 0)")
  (setq sub_changetype_dialog (start_dialog))
  (unload_dialog dcl_id)
  (if (= 1 sub_changetype_dialog);se clica em 'ok' 
    (progn
      (if (/= nil sgp_chtype_newtype);se algum tipo foi clicado
	(progn
	  (if (= sgp_chtype_newtype "sub_chtype_1")
	    (progn
	      (setq sgp_subtype "1")
	      (set_tile "lib_blktype" "Tipo: Reais")
	      (mode_tile "lib_blkunit" 0)
	      (mode_tile "sub_chunit" 0)
	    )
	    (progn
	      (setq sgp_subtype "2")
	      (set_tile "lib_blktype" "Tipo: Gráficos")
	      (mode_tile "lib_blkunit" 1)
	      (mode_tile "sub_chunit" 1)
	      (setq sgp_subunit "100")
	      (set_tile "lib_blkunit" "Unidade: Centímetros")
	    )
	  )	    
	  (grp_sgp_resave)
	)
      )
    )
  )      
)


;altera a cor do layer do subgrupo
(defun grp_sub_changecol ()
  (grp_sub_readprop)
  (setq new_color (acad_colordlg (fix (distof sgp_sublayc))))
  (if (/= nil new_color)
    (progn
      (setq sgp_sublayc (rtos new_color 2 0))
      (grp_sgp_resave)
      (start_image "lib_blklaycol")
      (fill_image  0  0
	(dimx_tile "lib_blklaycol")
	(dimy_tile "lib_blklaycol")
	(fix (distof sgp_sublayc))
	)
      (end_image)
    )
  )
)

;salva o arquivo de sub_propriedades, quando uma delas é alterada
(defun grp_sgp_resave ()
  (setq sub_ppdfile (strcat cnp_root "/slides/" lib_blkpfx lib_blkfam lib_blkgrp lib_blksub ".sgp")
	open_file (open sub_ppdfile "w" "utf8"))
  (write-line sgp_subtype open_file)
  (write-line sgp_subunit open_file)
  (write-line sgp_sublayn open_file)
  (write-line sgp_sublayc open_file)
  (close open_file)
)


;ao selecionar um subgrupo
(defun grp_sublist_action ()
  (setq grp_sublist_key $value)
  (if (= 1 (strlen grp_sublist_key)) (setq grp_sublist_key (strcat "0" grp_sublist_key)))
  (setq lib_blksub grp_sublist_key)
  (grp_sub_buttons_on)
  (grp_sub_readprop)
  (action_tile "lib_blklaycol" "(grp_sub_changecol)")
)

;ao selecionar um grupo, limpa as propriedades de subgrupo
(defun grp_sub_clearsgp ()
  (set_tile "lib_blktype" "")
  (set_tile "lib_blkunit" "")
  (set_tile "lib_blklayer" "")
  (start_image "lib_blklaycol")
  (fill_image  0  0
    (dimx_tile "lib_blklaycol")
    (dimy_tile "lib_blklaycol")
  -2)
  (end_image)
  (grp_buttons_off)
)
  
;lê as ropriedades do subgrupo selecionado
(defun grp_sub_readprop ()
  (setq sub_ppdfile (strcat cnp_root "/slides/" lib_blkpfx lib_blkfam lib_blkgrp lib_blksub ".sgp")
	open_file (open sub_ppdfile "r" "utf8")
	sgp_subtype (read-line open_file)
	sgp_subunit (read-line open_file)
	sgp_sublayn (read-line open_file)
	sgp_sublayc (read-line open_file)
  )
  (close open_file)
  (if (= sgp_subtype "1")
   (set_tile "lib_blktype" "Tipo: Reais")
   (progn
      (set_tile "lib_blktype" "Tipo: Gráficos")
      (set_tile "lib_blkunit" "Unidade: Centímetros")
      (mode_tile "lib_blkunit" 1)
      (mode_tile "sub_chunit" 1)
    )
  )
  (cond
    ((= sgp_subunit "1") (set_tile "lib_blkunit" "Unidade: Metros") (setq grp_unit "1"))
    ((= sgp_subunit "100") (set_tile "lib_blkunit" "Unidade: Centímetros") (setq grp_unit "100"))
    ((= sgp_subunit "1000") (set_tile "lib_blkunit" "Unidade: Milímetros") (setq grp_unit "1000"))
  )
  (set_tile "lib_blklayer" sgp_sublayn)
  (start_image "lib_blklaycol")
  (fill_image  0  0
    (dimx_tile "lib_blklaycol")
    (dimy_tile "lib_blklaycol")
    (fix (distof sgp_sublayc))
  )
  (end_image)
)
	

;grayon dos botões e grupos
(defun grp_sub_buttons_on ()
  (mode_tile "lib_sub_propbox" 0)
  (mode_tile "lib_sub_laybox" 0)
  (mode_tile "grp_sub_rename" 0)
  (mode_tile "grp_sub_new" 0)
  (mode_tile "grp_sub_prop" 0)
  (mode_tile "grp_sub_page" 0)
)


;botão Novo Grupo
(defun grp_grpnew_action () (cnp:unsupported "grp_grpnew_action"))

;nome do novo grupo
(defun grp_grpnew_getname ()
  (setq next_group (rtos (length lib_grplist) 2 0))
  (if (= 1 (strlen next_group)) (setq next_group (strcat "0" next_group)))
  (setq old_name (strcat "Grupo " next_group)
	new_name old_name)
  (setq dcl_id (load_dialog (strcat cnp_root "/lisp/cadnorma.dcl")))
  (if (not (new_dialog "grp_grprename_dcl" dcl_id)) (exit))
  (set_tile "grp_grprename_edit" old_name)
  (action_tile "grp_grprename_edit" "(setq new_name $value)")
  (mode_tile "grp_grprename_edit" 2)
  (action_tile "accept" "(done_dialog 1)")
  (action_tile "cancel" "(done_dialog 0)")
  (setq grp_grprename_dialog (start_dialog))
  (unload_dialog dcl_id)
  (if (= 0 grp_grprename_dialog) (exit))
  (if (= 1 grp_grprename_dialog) (grp_grpnew_getname_ok))
)


;botão ok -> salva nome novo
(defun grp_grpnew_getname_ok ()
  (setq open_file (open (strcat cnp_root "/slides/" lib_blkpfx lib_blkfam ".txt") "r" "utf8")
	new_list (list ""))
  (while (/= nil (setq linha (read-line open_file)))
    (setq new_list (append new_list (list linha)))
  )
  (close open_file)
  (setq new_list (append new_list (list new_name))
	new_list (cdr new_list))
  (setq open_file (open (strcat cnp_root "/slides/" lib_blkpfx lib_blkfam ".txt") "w" "utf8"))
  (foreach n new_list
    (write-line n open_file)
  )
  (close open_file)
)



  
;botão Renomear Grupo
(defun grp_grprename_action ()
  (setq ordem (read lib_blkgrp)
	old_name (nth ordem lib_grplist)
	new_name old_name)
  (setq dcl_id (load_dialog (strcat cnp_root "/lisp/cadnorma.dcl")))
  (if (not (new_dialog "grp_grprename_dcl" dcl_id)) (exit))
  (set_tile "grp_grprename_edit" old_name)
  (action_tile "grp_grprename_edit" "(setq new_name $value)")
  (mode_tile "grp_grprename_edit" 2)
  (action_tile "accept" "(done_dialog 1)")
  (action_tile "cancel" "(done_dialog 0)")
  (setq grp_grprename_dialog (start_dialog))
  (unload_dialog dcl_id)
  (if (= 1 grp_grprename_dialog) (grp_grprename_action_ok))
)

;botão ok -> salva nome novo
(defun grp_grprename_action_ok ()
  (setq cont 0 new_list (list ""))
  (foreach n lib_grplist
    (if (= cont ordem)
      (setq new_list (append new_list (list new_name)))
      (setq new_list (append new_list (list (nth cont lib_grplist))))
    )
    (setq cont (1+ cont))
  )
  (setq lib_grplist (cdr new_list))
  (setq open_file (open (strcat cnp_root "/slides/" lib_blkpfx lib_blkfam ".txt") "w" "utf8"))
  (foreach n lib_grplist
    (write-line n open_file)
  )
  (close open_file)
  (lib_manager)
)


;grayout dos botões
(defun grp_buttons_off ()
  (mode_tile "grp_grprename" 1)
  (mode_tile "grp_sub_rename" 1)
;;;  (mode_tile "grp_sub_new" 1)
  (mode_tile "grp_sub_prop" 1)
  (mode_tile "grp_sub_page" 1)
  (mode_tile "lib_sub_propbox" 1)
  (mode_tile "lib_sub_laybox" 1)
)

;ao selecionar um grupo, preenche o subgrupo
(defun grp_grplist_action ()
  (setq grp_grplist_key $value)
  (if (= 1 (strlen grp_grplist_key)) (setq grp_grplist_key (strcat "0" grp_grplist_key)))
  (setq lib_blkgrp grp_grplist_key)
  (lib_fillsub)
  (grp_sub_clearsgp)
  (mode_tile "grp_grprename" 0)
  (mode_tile "grp_grpnew" 0)
)


;******************************************************************************
;******************************************************************************
;Cadnorma Professional                                                         
;Argumentos de rede                                                            
;******************************************************************************
;******************************************************************************

;preenche o tipo biblioteca
(defun net_lib_label ()
  (setq lib_full_list (list "Símbolos Gerais"
			    "Arquitetura"
			    "Elétrica"
			    "Tubulações"
			    "Incêndio e SPDA"
			    "Baixa Tensão"
			    "Ar Condicionado"
			    "Estruturas de Concreto"
			    "Estruturas Metálicas"
			    "Topografia, Geologia e Mapas"
		       )
  )
  (start_list "newlib_label")
  (mapcar 'add_list lib_full_list)
  (end_list)
  (cond
    ((= lib_blkfam "sg")
     (setq lib_blkfam_code "0")
    )
    ((= lib_blkfam "aq")
     (setq lib_blkfam_code "1")
    )
    ((= lib_blkfam "el")
     (setq lib_blkfam_code "2")
    )
    ((= lib_blkfam "tu")
     (setq lib_blkfam_code "3")
    )
    ((= lib_blkfam "ic")
     (setq lib_blkfam_code "4")
    )
    ((= lib_blkfam "tl")
     (setq lib_blkfam_code "5")
    )
    ((= lib_blkfam "ac")
     (setq lib_blkfam_code "6")
    )
    ((= lib_blkfam "cc")
     (setq lib_blkfam_code "7")
    )
    ((= lib_blkfam "mt")
     (setq lib_blkfam_code "8")
    )
    ((= lib_blkfam "tp")
     (setq lib_blkfam_code "9")
    )
  )
  (set_tile "newlib_label" lib_blkfam_code)
  (action_tile "newlib_label" "(net_new_label_action)")
)

;label para gerenciador de bibliotecas
(defun net_lib_mng_label ()
  (setq lib_full_list (list "Símbolos Gerais"
			    "Arquitetura"
			    "Elétrica"
			    "Tubulações"
			    "Incêndio e SPDA"
			    "Baixa Tensão"
			    "Ar Condicionado"
			    "Estruturas de Concreto"
			    "Estruturas Metálicas"
			    "Topografia, Geologia e Mapas"
		       )
  )
  (start_list "newlib_label")
  (mapcar 'add_list lib_full_list)
  (end_list)
  (cond
    ((= lib_blkfam "sg")
     (setq lib_blkfam_code "0")
    )
    ((= lib_blkfam "aq")
     (setq lib_blkfam_code "1")
    )
    ((= lib_blkfam "el")
     (setq lib_blkfam_code "2")
    )
    ((= lib_blkfam "tu")
     (setq lib_blkfam_code "3")
    )
    ((= lib_blkfam "ic")
     (setq lib_blkfam_code "4")
    )
    ((= lib_blkfam "tl")
     (setq lib_blkfam_code "5")
    )
    ((= lib_blkfam "ac")
     (setq lib_blkfam_code "6")
    )
    ((= lib_blkfam "cc")
     (setq lib_blkfam_code "7")
    )
    ((= lib_blkfam "mt")
     (setq lib_blkfam_code "8")
    )
    ((= lib_blkfam "tp")
     (setq lib_blkfam_code "9")
    )
  )
  (set_tile "newlib_label" (strcat "Biblioteca de " (nth (fix (distof lib_blkfam_code)) lib_full_list)))
)


;ao selecionar uma família na DCL de Biblioteca (Professional)
(defun net_new_label_action ()
  (setq lib_blkfam_code $value)
  (cond
    ((= lib_blkfam_code "0") (setq lib_blkfam "sg"))
    ((= lib_blkfam_code "1") (setq lib_blkfam "aq"))
    ((= lib_blkfam_code "2") (setq lib_blkfam "el"))
    ((= lib_blkfam_code "3") (setq lib_blkfam "tu"))
    ((= lib_blkfam_code "4") (setq lib_blkfam "ic"))
    ((= lib_blkfam_code "5") (setq lib_blkfam "tl"))
    ((= lib_blkfam_code "6") (setq lib_blkfam "ac"))
    ((= lib_blkfam_code "7") (setq lib_blkfam "cc"))
    ((= lib_blkfam_code "8") (setq lib_blkfam "mt"))
    ((= lib_blkfam_code "9") (setq lib_blkfam "tp"))
  )
  (setq lib_blkgrp "00"
	lib_blksub "00"
	lib_blkpag "01"
	lib_blkblk "11"
  )
  (setq lib_blktog "0")
  (setq lib_inslay "0")
  (setq lib_explode "0")
  (net_lib_clearimg)
  (net_lib_dcl_action)
)


;distribuidor
(defun net_lib_cfgmain_lib ()
  (cn7_init)
  (if (or (= lib_blkfam nil)
	  (and (/= lib_blkfam "sg") (/= lib_blkfam "aq") (/= lib_blkfam "el") (/= lib_blkfam "tu")
	       (/= lib_blkfam "ic") (/= lib_blkfam "sg") (/= lib_blkfam "tl") (/= lib_blkfam "ac")
	       (/= lib_blkfam "cc") (/= lib_blkfam "mt") (/= lib_blkfam "tp")))
    (setq lib_blkfam "sg")
  )
  (if lib_blkfam_bkp
    (if (and
	  (= lib_blkfam_bkp lib_blkfam)
	  (findfile (strcat cnp_netroot "/slides/" lib_blkpfx lib_blkfam lib_blkgrp lib_blksub lib_blkpag ".txt"))
	)
      (net_lib_cfg_file)
      (progn
	(setq lib_blkgrp "00")
	(setq lib_blksub "00")
	(setq lib_blkpag "01")
	(setq lib_blkblk "11")
      )
    )
    (progn
      (setq file (open (strcat cnp_root "/config/lastlib.txt") "w" "utf8"))
      (write-line "00" file)
      (write-line "00" file)
      (write-line "01" file)
      (write-line "11" file)
      (write-line "1.0" file)
      (close file)
      (net_lib_cfg_file)
    )
  )
  (setq lib_blkfam_bkp lib_blkfam)
  (net_lib_dcl)
  (if (= lib_cfgmain_return 1) (net_lib_cfg_main))
)

;lê os dados iniciais da DCL no arquivo de dados
(defun net_lib_cfg_file ()
  (if (findfile (strcat cnp_root "/config/lastlib.txt"))
    (net_lib_lastlib_readfile)
    (progn
      (setq file (open (strcat cnp_root "/config/lastlib.txt") "w" "utf8"))
      (write-line "00" file)
      (write-line "00" file)
      (write-line "01" file)
      (write-line "11" file)
      (write-line "1.0" file)
      (close file)
      (net_lib_lastlib_readfile)
    )
  )
)

;;;;função que lê o arquivo de dados
;;;(defun net_lib_lastlib_readfile ()
;;;  (setq	file (open (strcat cnp_root "/config/lastlib.txt") "r"))
;;;  (setq	lib_blkgrp (read-line file))
;;;  (setq	lib_blksub (read-line file))
;;;  (setq	lib_blkpag (read-line file))
;;;  (setq	lib_blkblk (read-line file))
;;;  (setq	lib_blkscl (read-line file))
;;;  (close file)
;;;)

(defun net_lib_lastlib_readfile ()
  (if (= nil lib_blkgrp) (setq lib_blkgrp "00"))
  (if (= nil lib_blksub) (setq lib_blksub "00"))
  (if (= nil lib_blkpag) (setq lib_blkpag "01"))
  (if (= nil lib_blkblk) (setq lib_blkblk "11"))
  (if (= nil lib_blkscl) (setq lib_blkscl "1.0"))
)

;caixa de diálogo
(defun net_lib_dcl ()
  (setq lib_blktog "0")
  (setq lib_explode "0")
  ;abre a dcl
  (setq dcl_id (load_dialog (strcat cnp_root "/lisp/cadnorma.dcl")))
  (cond
    ((= lib_type "admin") (if (not (new_dialog "new_library4" dcl_id)) (exit)))
    ((= lib_type "user") (if (not (new_dialog "new_library3" dcl_id)) (exit)))
    ((= lib_type "fabr") (if (not (new_dialog "new_library5" dcl_id)) (exit)))
    ((= lib_type "fabr2") (if (not (new_dialog "new_library2" dcl_id)) (exit)))
  )
  (net_lib_dcl_action)
;;;  (lib_label)
  (if (= nil lib_inslay) (setq lib_inslay "0"))
  (set_tile "lib_insert_curlay" lib_inslay)
  (action_tile "lib_insert_curlay" "(setq lib_inslay $value)")
  (action_tile "lib_insert_explode" "(setq lib_explode $value)")
  (action_tile "lib_grplist" "(net_lib_action_grplist)")
  (action_tile "lib_sublist" "(net_lib_action_sublist)")
  (action_tile "lib_paglist" "(net_lib_action_paglist)")
  (action_tile "lib_blknext" "(net_lib_action_next)")
  (action_tile "lib_blkprev" "(net_lib_action_prev)")
  (action_tile "lib_blkredef" "(done_dialog 2)")
  (action_tile "lib_blkslide" "(done_dialog 3)")
  (action_tile "lib_blkclear" "(done_dialog 4)")
  (action_tile "lib_blkamplify" "(done_dialog 5)")
  (action_tile "lib_descr_altera" "(done_dialog 6)")
  (action_tile "lib_descr_insere" "(done_dialog 10)")
  (action_tile "lib_blkexchange" "(done_dialog 7)")
  (action_tile "lib_blkupdate" "(done_dialog 8)")
  (action_tile "lib_grpmng" "(done_dialog 9)")
  (action_tile "sub_chlayn" "(net_grp_sub_changenlay)")
  (action_tile "lib_blklaycol2" "(net_grp_sub_changecol)")
  (action_tile "lib_sclblk_toggle" "(setq lib_blktog $value)")
  (action_tile "lib_sclblk_factor" "(setq lib_blkscl $value)")
  (action_tile "icon11" "(net_lib_action_icon)")
  (action_tile "icon12" "(net_lib_action_icon)")
  (action_tile "icon13" "(net_lib_action_icon)")
  (action_tile "icon14" "(net_lib_action_icon)")
  (action_tile "icon21" "(net_lib_action_icon)")
  (action_tile "icon22" "(net_lib_action_icon)")
  (action_tile "icon23" "(net_lib_action_icon)")
  (action_tile "icon24" "(net_lib_action_icon)")
  (action_tile "icon31" "(net_lib_action_icon)")
  (action_tile "icon32" "(net_lib_action_icon)")
  (action_tile "icon33" "(net_lib_action_icon)")
  (action_tile "icon34" "(net_lib_action_icon)")
  (action_tile "icon41" "(net_lib_action_icon)")
  (action_tile "icon42" "(net_lib_action_icon)")
  (action_tile "icon43" "(net_lib_action_icon)")
  (action_tile "icon44" "(net_lib_action_icon)")
  (action_tile "lib_blkinsert" "(done_dialog 1)")
  (action_tile "lib_blkclose" "(done_dialog 0)")
  (action_tile "cancel" "(done_dialog 0)")
  (setq cn_lastlib_dialog (start_dialog))
  (unload_dialog dcl_id)
  ;o que fazer depois
  (if (= 0 cn_lastlib_dialog) (net_lib_save_lastlib))
  (if (= 1 cn_lastlib_dialog) (net_lib_lastlib_insert))
  (if (= 2 cn_lastlib_dialog) (net_lib_action_redef))
  (if (= 3 cn_lastlib_dialog) (net_lib_action_slide))
  (if (= 4 cn_lastlib_dialog) (net_lib_action_clear))
  (if (= 5 cn_lastlib_dialog) (net_lib_action_amplify))
  (if (= 6 cn_lastlib_dialog) (net_lib_action_descript))
  (if (= 7 cn_lastlib_dialog) (net_lib_action_exchange))
  (if (= 8 cn_lastlib_dialog) (net_lib_action_blkupdate))
  (if (= 9 cn_lastlib_dialog) (net_lib_manager))
  (if (= 10 cn_lastlib_dialog) (net_lib_action_descript2))
)

(defun net_lib_dcl_action ()
  ;preenchimento da dcl
  (if (and (/= lib_type "fabr") (/= lib_type "fabr2")) (net_lib_label))
  (net_lib_fillgrp)
  (net_lib_fillsub)
  (net_lib_fillpag)
  (net_lib_fillimg)
  (net_lib_fillgpp)
  (net_lib_fill_currpage)
  (net_lib_scaleblock)
  ;estados iniciais dos tiles
  (mode_tile "lib_blklaycol" 1)
  (mode_tile "lib_blkprev" 1)
  (mode_tile "lib_blknext" 1)
  (mode_tile "lib_descr_altera" 1)
  (mode_tile "lib_descr_insere" 1)
  (net_lib_blk_grayout)
  (set_tile "lib_grplist" (rtos (distof lib_blkgrp) 2 0))
  (set_tile "lib_sublist" (rtos (distof lib_blksub) 2 0))
  (set_tile "lib_sclblk_factor" lib_blkscl)
  (net_lib_nextprev)
  ;ações das listas
)

;**************************************************
;função que escreve a descrição do bloco no desenho
;**************************************************
(defun net_lib_action_descript2 ()
  (net_lib_save_lastlib)
  (setq n_descr (fix (distof lib_paglist_key))
	curr_descr (nth n_descr lib_paglist))
  (net_lib_action_descript3)
)

(defun net_lib_action_descript3 ()
  (setq psimb_txt nil pt1 nil)
  (net_lib_descr_readfile)
  (initget 128)
  (setq pt1 (getpoint "\nModel Space/Layout/Formatar texto/Editar Texto/<Ponto de inserção do texto...> "))
  (cond
    ((= 'LIST (type pt1))
     (setq psimb_txt pt1)
     (net_lib_descr_writext)
     )
    ((= 'STR  (type pt1))
     (cond
       ((= "F" (strcase pt1))
	(net_lib_descr_format)
	(net_lib_action_descript2))
       ((= "E" (strcase pt1))
	(net_lib_descr_modify))
       ((= "M" (strcase pt1))
	(command "._tilemode" "1")
	(net_lib_action_descript2))
       ((= "L" (strcase pt1))
	(command "._tilemode" "0" "._pspace")
	(net_lib_action_descript2))
       (t
	(prompt "\nOpção inválida! Digite F, E, M, L ou Clique no ponto de Inserção...")
	(net_lib_action_descript2))
      );cond
     )
   );cond
)

;modifica texto existente
(defun net_lib_descr_modify ()
  (prompt "\nSelecione um texto para receber a descrição... ")
  (setq ent2 (entsel)
	ent2_list (entget (car ent2))
	ent2_type (cdr (assoc 0 ent2_list)))
  (if (/= "TEXT" (strcase ent2_type))
    (progn
      (alert "Entidade não é um texto!")
      (net_lib_descr_modify)
    )
    (progn
      (entmod (setq ent2_list (subst (cons 1 curr_descr) (assoc 1 ent2_list) ent2_list)))
    )
  )
)
	


;escreve o texto da descrição
(defun net_lib_descr_writext ()
  (setq txdescr_stylist (list "r50" "r60" "r70" "r80" "r90" "r100" "r120" "r140" "r175" "r200"
			    "t1" "t2" "t3" "t4" "t5" "t6" "t7")
	blkdescr_style (nth (fix (distof blkdescr_sty)) txdescr_stylist)
  )
  (if (= "1" blkdescr_cxa) (setq curr_descr (strcase curr_descr)))
  (cn7_verylayer "Blocos_descrição" 2)  
  (cn7_txsimb blkdescr_style "bl" curr_descr (fix (distof blkdescr_col)) blkdescr_lay 0)
)


;formatação do texto de legenda
(defun net_lib_descr_format ()
  (setq dcl_id (load_dialog (strcat cnp_root "/lisp/cadnorma.dcl")))
  (if (not (new_dialog "cn9_descr_sty" dcl_id)) (exit))
  ;estilo do texto
  (setq txdescr_stylist (list "r50" "r60" "r70" "r80" "r90" "r100" "r120" "r140" "r175" "r200"
			    "t1" "t2" "t3" "t4" "t5" "t6" "t7"))
  (start_list "cn9_descr_style")
  (mapcar 'add_list txdescr_stylist)
  (end_list)
  (set_tile "cn9_descr_style" blkdescr_sty)
  (action_tile "cn9_descr_style" "(setq blkdescr_sty $value)")
  ;cor do texto
  (start_image "cn9_descr_color")
  (fill_image  0  0
    (dimx_tile "cn9_descr_color")
    (dimy_tile "cn9_descr_color")
    (fix (distof blkdescr_col))
  )
  (end_image)
  (action_tile "cn9_descr_color" "(net_cn9_descr_txcol)")
  ;layer de inserção
  (set_tile "cn9_descr_layer" blkdescr_lay)
  (action_tile "cn9_descr_layer" "(setq blkdescr_lay $value)")
  ;Escrever em maiúscula
  (set_tile "cn9_descr_cxa" blkdescr_cxa)
  (action_tile "cn9_descr_cxa" "(setq blkdescr_cxa $value)")
  ;ok_cancel
  (action_tile "cancel" "(done_dialog 0)")
  (action_tile "accept" "(done_dialog 1)")
  (setq lib_descr_dcl (start_dialog))
  (unload_dialog dcl_id)
  (if (= lib_descr_dcl 1) (net_lib_descr_writefile))
);defun


;define a cor do texto de descrição
;escolher cor do texto
(defun net_cn9_descr_txcol ()
  (setq cn9_descr_newcol (acad_colordlg (fix (distof blkdescr_col))))
  (if (/= nil cn9_descr_newcol) (setq blkdescr_col (rtos cn9_descr_newcol 2 0)))
  (start_image "cn9_descr_color")
  (fill_image  0  0
    (dimx_tile "cn9_descr_color")
    (dimy_tile "cn9_descr_color")
    (fix (distof blkdescr_col))
  )
  (end_image)
)
;escreve o arquivo de descrição
(defun net_lib_descr_writefile ()
  (setq file (open (strcat cnp_root "/config/blkdescr.txt") "w" "utf8"))
  (write-line blkdescr_sty file)
  (write-line blkdescr_col file)
  (write-line blkdescr_lay file)
  (write-line blkdescr_cxa file)
  (close file)
)

;lê o arquivo de descrição
(defun net_lib_descr_readfile ()
  (if (not (findfile (strcat cnp_root "/config/blkdescr.txt")))
    (progn
      (setq file (open (strcat cnp_root "/config/blkdescr.txt") "w" "utf8"))
      (write-line "3" file)
      (write-line "2" file)
      (write-line "Blocos_descrição" file)
      (write-line "1" file)
      (close file)
    )
  )
  ;procura o valor padrão
  (setq	file (open (strcat cnp_root "/config/blkdescr.txt") "r" "utf8"))
  (setq blkdescr_sty (read-line file))
  (setq blkdescr_col (read-line file))
  (setq blkdescr_lay (read-line file))
  (setq blkdescr_cxa (read-line file))
  (close file)
)


;**************************************************
;função que escreve a descrição do bloco no desenho
;**************************************************
(defun c:net_blkd ()
  (prompt "\nSelecione um bloco para escrever sua descrição... ")
  (setq ent (entsel)
	ent_list (entget (car ent))
	ent_type (cdr (assoc 0 ent_list)))
  (if (= "INSERT" (strcase ent_type))
    (progn
      (setq ent_blkname (cdr (assoc 2 ent_list)))
      (net_blkd_testnorma)
    )
  )
  (princ)
)

;define se é bloco do Cadnorma
(defun net_blkd_testnorma ();teste
  (setq counter nil)
  (if (and
	(= 14 (strlen ent_blkname))
	(findfile (strcat cnp_netroot "/slides/" (substr ent_blkname 1 12) ".txt"))
      )
    (progn
      (setq blkd_ordem (substr ent_blkname 13 2))
      (cond
	((= blkd_ordem "11") (setq counter 1))
	((= blkd_ordem "12") (setq counter 2))
	((= blkd_ordem "13") (setq counter 3))
	((= blkd_ordem "14") (setq counter 4))
	((= blkd_ordem "21") (setq counter 5))
	((= blkd_ordem "22") (setq counter 6))
	((= blkd_ordem "23") (setq counter 7))
	((= blkd_ordem "24") (setq counter 8))
	((= blkd_ordem "31") (setq counter 9))
	((= blkd_ordem "32") (setq counter 10))
	((= blkd_ordem "33") (setq counter 11))
	((= blkd_ordem "34") (setq counter 12))
	((= blkd_ordem "41") (setq counter 13))
	((= blkd_ordem "42") (setq counter 14))
	((= blkd_ordem "43") (setq counter 15))
	((= blkd_ordem "44") (setq counter 16))
    );cond
      (setq open_file (open (strcat cnp_netroot "/slides/" (substr ent_blkname 1 12) ".txt") "r" "utf8"))
      (repeat counter
	(setq blkd_descr (read-line open_file))
      )
      (close open_file)
      (cn7_alert_yes_no "Descrição do bloco:" blkd_descr "Deseja transcrever para o desenho?")
      (if (= alert_resp "yes")
	(progn
	  (setq curr_descr blkd_descr)
	  (net_lib_action_descript3)
	)
      );if
   );progn
   (alert "O bloco selecionado\nnão pertence à Biblioteca\ndo Cadnorma!"))
)


;preenche página atual / total de páginas
(defun net_lib_fill_currpage ()
  (net_lib_findpages)
  (set_tile "lib_current_page" (strcat "Pág.: " lib_blkpag " / " lib_numpaginas))
)

;encontrar o número de páginas de um subgrupo
(defun net_lib_findpages ()
  (setq lib_currpage 1)
  (lib_findpages_findnext)
  (while (findfile lib_nextpage_file)
      (setq lib_currpage (1+ lib_currpage))
      (lib_findpages_findnext)
  )
  (setq lib_numpaginas (rtos lib_currpage 2 0))
  (if (= 1 (strlen lib_numpaginas)) (setq lib_numpaginas (strcat "0" lib_numpaginas)))
)

;encontra o nome do próximo arquivo de página
(defun net_lib_findpages_findnext ()
  (setq	lib_nextpage (1+ lib_currpage)
	lib_nextpage_str (rtos lib_nextpage 2 0))
  (if (= 1 (strlen lib_nextpage_str)) (setq lib_nextpage_str (strcat "0" lib_nextpage_str)))
  (setq lib_nextpage_file (strcat cnp_netroot "/slides/" lib_blkpfx lib_blkfam lib_blkgrp lib_blksub lib_nextpage_str ".txt"))
)

;botão 'Conflitos'
(defun net_lib_action_blkupdate ()
  (net_lib_save_lastlib)
  (setq dcl_id (load_dialog (strcat cnp_root "/lisp/cadnorma.dcl")))
  (if (not (new_dialog "lib_blk_update" dcl_id)) (exit))
  (set_tile "blk_updt_radio" "blk_updt_update")
  (setq lib_blkupdt_action "blk_updt_update")
  (action_tile "blk_updt_radio" "(setq lib_blkupdt_action $value)")
  (action_tile "accept" "(done_dialog 1)")
  (action_tile "cancel" "(done_dialog 0)")
  (setq lib_atualizar (start_dialog))
  (unload_dialog dcl_id)
  (if (= 1 lib_atualizar) (net_lib_updblk_update))
)


(defun net_lib_updblk_update ()
  (setq dwg_blk (strcat lib_blkpfx lib_blkfam lib_blkgrp lib_blksub lib_blkpag lib_blkblk))
  (setq dwg_blk_file (strcat cnp_netroot "/blocos/" dwg_blk ".dwg"))
  (if (not (tblsearch "block" dwg_blk))
    (alert "\nNao existem definições desse bloco no desenho...")
    (progn
      (setq counter 1)
      (net_find_next_temp)
      (command "._rename" "_b" dwg_blk curr_temp)
      (if (= lib_blkupdt_action "blk_updt_update")
	(progn
	  (command "._insert" dwg_blk_file "_non" "0,0" "" "" "")
	  (command "._explode" (entlast))
	  (command "._block" curr_temp "_y" "0,0" "_p" "")
	  (command "._rename" "_b" dwg_blk next_temp)
	  (command "._rename" "_b" curr_temp dwg_blk)
	  (command "._rename" "_b" next_temp curr_temp)
	  (cn7_alert_ok
	    "O Cadnorma renomeou o bloco antigo para"
	    curr_temp
	    "Use o comando <PURGE> para eliminá-lo...")
        );progn case T
	(progn
	  (cn7_alert_ok
	    "O Cadnorma renomeou o bloco antigo para"
	    curr_temp
	    "Insira normalmente o novo bloco...")
	  (lib_dcl)
	);progn case F
      );if
    );progn
  );if
);defun

(defun net_find_next_temp ()
  (setq curr_temp (strcat "Renomeado_" (rtos counter 2 0)))
  (if (tblsearch "block" curr_temp)
    (progn
      (setq counter (1+ counter))
      (net_find_next_temp)
    );progn
    (setq next_temp (strcat "Renomeado_" (rtos (1+ counter) 2 0)))
  );if
);defun


  
;botão 'Substituir'
(defun net_lib_action_exchange ()
  (net_lib_save_lastlib)
  (if (not (findfile lib_currdwg))
    (progn
      (cn7_alert_ok
	"Impossível operar substituição"
	"de blocos com ícones vazios!"
	"Selecione um ícone ocupado...")
      (net_lib_dcl)
    )
    (progn
      (prompt "\nSelecione um dos blocos que deseja substituir... ")
      (setq lib_blkproto (entsel)
	    lib_blkproto_type (cdr (assoc 0 (entget (car lib_blkproto)))))
      (if (/= "INSERT" lib_blkproto_type)
	(progn
	  (alert "Objeto selecionado\nnão é um bloco!\nTente novamente...")
	  (lib_action_exchange)
	  )
	(progn
	  (setq lib_blkproto_name (cdr (assoc 2 (entget (car lib_blkproto)))))
	  (prompt "Selecione os objetos ou área para substituir os blocos...<ENTER> para anterior... ")
	  (setq exchange_sel (ssget '((0 . "INSERT"))))
	  (if (= nil exchange_sel)
	    (progn
	      (setq exchange_sel (ssadd))
	      (setq exchange_sel (ssadd (car lib_blkproto) exchange_sel))
	      )
	    )
	  (setq exchange_sel_n (sslength exchange_sel)
		counter 0)
	  (repeat exchange_sel_n
	    (setq entname (ssname exchange_sel counter)
		  ent_blkname (cdr (assoc 2 (entget entname)))
		  ent_insert (cdr (assoc 10 (entget entname)))
		  ent_scale (cdr (assoc 41 (entget entname)))
		  ent_rotation (cdr (assoc 50 (entget entname)))
		  angdeg (/ (* 180 ent_rotation) pi))
	    (if (= lib_blkproto_name ent_blkname)
	      (progn
		(command "._erase" entname "")
		(cn7_find_blkscl)
		(setq pt1 ent_insert)
		(cn7_verylayer (strcat cn7_blk_prefixlay lib_currsgp_layname) (fix (distof lib_currsgp_laycol)));***
		(command "._insert" lib_currdwg "_scale" cn7_blkscl "_non" pt1 angdeg);***
		)
	      )
	    (setq counter (1+ counter))
	    )
	  )
	)
    )
  )
)

;botão 'Descrição'
(defun net_lib_action_descript ()
  (net_lib_save_lastlib)
  (setq dcl_id (load_dialog (strcat cnp_root "/lisp/cadnorma.dcl")))
  (if (not (new_dialog "cn7_red_descript" dcl_id)) (exit))
  (setq n_descr (fix (distof lib_paglist_key))
	curr_descr (nth n_descr lib_paglist))
  (set_tile "cn7_chg_descript" curr_descr)
  (mode_tile "cn7_chg_descript" 2)
  (action_tile "cn7_chg_descript" "(setq cn7_new_descr $value)")
  (action_tile "accept" "(done_dialog 1)")
  (action_tile "cancel" "(done_dialog 0)")
  (setq chg_descr (start_dialog))
  (unload_dialog dcl_id)
  (if (= chg_descr 1) (progn (net_lib_chg_descript) (net_lib_dcl)))
)


;atualiza o arquivo de descrições da página
(defun net_lib_chg_descript ()
  (setq counter 0 lib_newpaglist (list))
  (repeat 16
    (if (= counter n_descr)
      (setq lib_newpaglist (append lib_newpaglist (list cn7_new_descr)))
      (setq lib_newpaglist (append lib_newpaglist (list (nth counter lib_paglist))))
    )
    (setq counter (1+ counter))
    (setq open_file (open (strcat cnp_netroot "/slides/" lib_blkpfx lib_blkfam lib_blkgrp lib_blksub lib_blkpag ".txt") "w" "utf8"))
    (foreach n lib_newpaglist
      (write-line n open_file)
    )
    (close open_file)
  )
)


;botão ampliar
(defun net_lib_action_amplify ()
  (net_lib_save_lastlib)
  (setq dcl_id2 (load_dialog (strcat cnp_root "/lisp/cadnorma.dcl")))
  (if (not (new_dialog "lib_amplify" dcl_id2)) (exit))
  (setq x (dimx_tile "sld_amplify")
	y (dimy_tile "sld_amplify"))
  (start_image "sld_amplify")
  (slide_image 0 0 x y curr_icon);curr_icon
  (end_image)
  (setq n_descr (fix (distof lib_paglist_key))
	curr_descr (nth n_descr lib_paglist))
  (set_tile "lib_amplify_descript" curr_descr)
  (action_tile "lib_amplify_insert" "(done_dialog 2)")
  (action_tile "accept" "(done_dialog 1)")
  (action_tile "cancel" "(done_dialog 0)")
  (setq lib_amp (start_dialog))
  (unload_dialog dcl_id2)
  (if (= 0 lib_amp) (net_lib_dcl))
  (if (= 1 lib_amp) (net_lib_dcl))
  (if (= 2 lib_amp) (net_lib_lastlib_insert))
)

;botão Limpar
(defun net_lib_action_clear () (cnp:unsupported "net_lib_action_clear"))

;troca / por \\ no nome do arquivo
(defun net_transf_dwg_name ()
  (setq n (strlen lib_currdwg) count 1 new_dwg "")
  (repeat n
    (if (= (substr lib_currdwg count 1) "/")
      (setq new_dwg (strcat new_dwg "\\"))
      (setq new_dwg (strcat new_dwg (substr lib_currdwg count 1)))
      );if
    (setq count (1+ count))
  );repeat
);defun

;troca / por \\ no nome do slide
(defun net_transf_sld_name ()
  (setq n (strlen lib_currsld) count 1 new_sld "")
  (repeat n
    (if (= (substr lib_currsld count 1) "/")
      (setq new_sld (strcat new_sld "\\"))
      (setq new_sld (strcat new_sld (substr lib_currsld count 1)))
      );if
    (setq count (1+ count))
  );repeat
);defun


;botão Slide
(defun net_lib_action_slide () (cnp:unsupported "net_lib_action_slide"))


;botão Redefinir
(defun net_lib_action_redef () (cnp:unsupported "net_lib_action_redef"))

;cria o arquivo de slides a serem gerados
(defun net_lib_writeslb ()
  (setq open_file (open (strcat cnp_netroot "/slides/cadnslides.txt") "w" "utf8"))
  (write-line (strcat cnp_netroot "/slides/" lib_blkpfx lib_blkfam lib_blkgrp lib_blksub lib_blkpag "11") open_file)
  (write-line (strcat cnp_netroot "/slides/" lib_blkpfx lib_blkfam lib_blkgrp lib_blksub lib_blkpag "12") open_file)
  (write-line (strcat cnp_netroot "/slides/" lib_blkpfx lib_blkfam lib_blkgrp lib_blksub lib_blkpag "13") open_file)
  (write-line (strcat cnp_netroot "/slides/" lib_blkpfx lib_blkfam lib_blkgrp lib_blksub lib_blkpag "14") open_file)
  (write-line (strcat cnp_netroot "/slides/" lib_blkpfx lib_blkfam lib_blkgrp lib_blksub lib_blkpag "21") open_file)
  (write-line (strcat cnp_netroot "/slides/" lib_blkpfx lib_blkfam lib_blkgrp lib_blksub lib_blkpag "22") open_file)
  (write-line (strcat cnp_netroot "/slides/" lib_blkpfx lib_blkfam lib_blkgrp lib_blksub lib_blkpag "23") open_file)
  (write-line (strcat cnp_netroot "/slides/" lib_blkpfx lib_blkfam lib_blkgrp lib_blksub lib_blkpag "24") open_file)
  (write-line (strcat cnp_netroot "/slides/" lib_blkpfx lib_blkfam lib_blkgrp lib_blksub lib_blkpag "31") open_file)
  (write-line (strcat cnp_netroot "/slides/" lib_blkpfx lib_blkfam lib_blkgrp lib_blksub lib_blkpag "32") open_file)
  (write-line (strcat cnp_netroot "/slides/" lib_blkpfx lib_blkfam lib_blkgrp lib_blksub lib_blkpag "33") open_file)
  (write-line (strcat cnp_netroot "/slides/" lib_blkpfx lib_blkfam lib_blkgrp lib_blksub lib_blkpag "34") open_file)
  (write-line (strcat cnp_netroot "/slides/" lib_blkpfx lib_blkfam lib_blkgrp lib_blksub lib_blkpag "41") open_file)
  (write-line (strcat cnp_netroot "/slides/" lib_blkpfx lib_blkfam lib_blkgrp lib_blksub lib_blkpag "42") open_file)
  (write-line (strcat cnp_netroot "/slides/" lib_blkpfx lib_blkfam lib_blkgrp lib_blksub lib_blkpag "43") open_file)
  (write-line (strcat cnp_netroot "/slides/" lib_blkpfx lib_blkfam lib_blkgrp lib_blksub lib_blkpag "44") open_file)
  (close open_file)
)
  
;botão próxima
(defun net_lib_action_next ()
  (setq lib_blkpag next_page_str)
  (net_lib_clearimg)
  (net_lib_fillimg)
  (net_lib_fillpag)
  (net_lib_nextprev)
  (net_lib_fill_currpage)
)

;botão anterior
(defun net_lib_action_prev ()
  (setq lib_blkpag prev_page_str)
  (net_lib_clearimg)
  (net_lib_fillimg)
  (net_lib_fillpag)
  (net_lib_nextprev)
  (net_lib_fill_currpage)
)

;verifica se existe próxima e anterior
(defun net_lib_nextprev ()
  (setq curr_page (fix (distof lib_blkpag))
	next_page (1+ curr_page)
	next_page_str (rtos next_page 2 0)
	prev_page (1- curr_page)
	prev_page_str (rtos prev_page 2 0))
  (if (= 1 (strlen next_page_str)) (setq next_page_str (strcat "0" next_page_str)))
  (if (= 1 (strlen prev_page_str)) (setq prev_page_str (strcat "0" prev_page_str)))
  (setq next_page_file (strcat cnp_netroot "/slides/" lib_blkpfx lib_blkfam lib_blkgrp lib_blksub next_page_str ".txt")
	prev_page_file (strcat cnp_netroot "/slides/" lib_blkpfx lib_blkfam lib_blkgrp lib_blksub prev_page_str ".txt")
  )
  (if (findfile next_page_file) (mode_tile "lib_blknext" 0) (mode_tile "lib_blknext" 1))
  (if (findfile prev_page_file) (mode_tile "lib_blkprev" 0) (mode_tile "lib_blkprev" 1))
)

;grayout nos botões de bloco selecionado
(defun net_lib_blk_grayout ()
  (mode_tile "lib_blkredef" 1)
  (mode_tile "lib_blkslide" 1)
  (mode_tile "lib_blkclear" 1)
  (mode_tile "lib_blkamplify" 1)
  (mode_tile "lib_blkupdate" 1)
  (mode_tile "lib_blkinsert" 1)
  (mode_tile "lib_descr_altera" 1)
  (mode_tile "lib_descr_escreve" 1)
  (mode_tile "lib_blkexchange" 1)
)

;grayout nos botões de bloco selecionado
(defun net_lib_blk_grayin ()
  (mode_tile "lib_blkredef" 0)
  (mode_tile "lib_blkslide" 0)
  (mode_tile "lib_blkclear" 0)
  (mode_tile "lib_blkamplify" 0)
  (mode_tile "lib_blkupdate" 0)
  (mode_tile "lib_blkinsert" 0)
  (mode_tile "lib_descr_altera" 0)
  (mode_tile "lib_descr_insere" 0)
  (mode_tile "lib_blkexchange" 0)
)

  
;ao selecionar um icon
;acende o item correspondente na listagem
(defun net_lib_action_icon ()
  (net_lib_blk_grayin)
  (setq lib_blkblk (substr $key 5 2))
  (cond
    ((= lib_blkblk "11") (setq lib_paglist_key "00") (set_tile "lib_paglist" "0"))
    ((= lib_blkblk "12") (setq lib_paglist_key "01") (set_tile "lib_paglist" "1"))
    ((= lib_blkblk "13") (setq lib_paglist_key "02") (set_tile "lib_paglist" "2"))
    ((= lib_blkblk "14") (setq lib_paglist_key "03") (set_tile "lib_paglist" "3"))
    ((= lib_blkblk "21") (setq lib_paglist_key "04") (set_tile "lib_paglist" "4"))
    ((= lib_blkblk "22") (setq lib_paglist_key "05") (set_tile "lib_paglist" "5"))
    ((= lib_blkblk "23") (setq lib_paglist_key "06") (set_tile "lib_paglist" "6"))
    ((= lib_blkblk "24") (setq lib_paglist_key "07") (set_tile "lib_paglist" "7"))
    ((= lib_blkblk "31") (setq lib_paglist_key "08") (set_tile "lib_paglist" "8"))
    ((= lib_blkblk "32") (setq lib_paglist_key "09") (set_tile "lib_paglist" "9"))
    ((= lib_blkblk "33") (setq lib_paglist_key "10") (set_tile "lib_paglist" "10"))
    ((= lib_blkblk "34") (setq lib_paglist_key "11") (set_tile "lib_paglist" "11"))
    ((= lib_blkblk "41") (setq lib_paglist_key "12") (set_tile "lib_paglist" "12"))
    ((= lib_blkblk "42") (setq lib_paglist_key "13") (set_tile "lib_paglist" "13"))
    ((= lib_blkblk "43") (setq lib_paglist_key "14") (set_tile "lib_paglist" "14"))
    ((= lib_blkblk "44") (setq lib_paglist_key "15") (set_tile "lib_paglist" "15"))
  )
  (net_lib_blkfiles)
)


;ao selecionar um bloco da lista:
;	acende o icon correspondente
;
(defun net_lib_action_paglist ()
  (net_lib_blk_grayin)
  (setq lib_paglist_key $value)
  (if (= 1 (strlen lib_paglist_key)) (setq lib_paglist_key (strcat "0" lib_paglist_key)))
  (cond
    ((= lib_paglist_key "00") (setq lib_blkblk "11") (mode_tile "icon11" 2))
    ((= lib_paglist_key "01") (setq lib_blkblk "12") (mode_tile "icon12" 2))
    ((= lib_paglist_key "02") (setq lib_blkblk "13") (mode_tile "icon13" 2))
    ((= lib_paglist_key "03") (setq lib_blkblk "14") (mode_tile "icon14" 2))
    ((= lib_paglist_key "04") (setq lib_blkblk "21") (mode_tile "icon21" 2))
    ((= lib_paglist_key "05") (setq lib_blkblk "22") (mode_tile "icon22" 2))
    ((= lib_paglist_key "06") (setq lib_blkblk "23") (mode_tile "icon23" 2))
    ((= lib_paglist_key "07") (setq lib_blkblk "24") (mode_tile "icon24" 2))
    ((= lib_paglist_key "08") (setq lib_blkblk "31") (mode_tile "icon31" 2))
    ((= lib_paglist_key "09") (setq lib_blkblk "32") (mode_tile "icon32" 2))
    ((= lib_paglist_key "10") (setq lib_blkblk "33") (mode_tile "icon33" 2))
    ((= lib_paglist_key "11") (setq lib_blkblk "34") (mode_tile "icon34" 2))
    ((= lib_paglist_key "12") (setq lib_blkblk "41") (mode_tile "icon41" 2))
    ((= lib_paglist_key "13") (setq lib_blkblk "42") (mode_tile "icon42" 2))
    ((= lib_paglist_key "14") (setq lib_blkblk "43") (mode_tile "icon43" 2))
    ((= lib_paglist_key "15") (setq lib_blkblk "44") (mode_tile "icon44" 2))
  )
  (net_lib_blkfiles)
)

;rotina chave:define os arquivos relacionados a um bloco
(defun net_lib_blkfiles ()
  (setq lib_currdwg (strcat cnp_netroot "/blocos/" lib_blkpfx lib_blkfam lib_blkgrp lib_blksub lib_blkpag lib_blkblk ".dwg")
	lib_currsld (strcat cnp_netroot "/slides/" lib_blkpfx lib_blkfam lib_blkgrp lib_blksub lib_blkpag lib_blkblk ".sld")
	lib_currslb (strcat cnp_netroot "/slides/" lib_blkpfx lib_blkfam lib_blkgrp lib_blksub lib_blkpag)
	curr_icon (strcat cnp_netroot "/slides/" lib_blkpfx lib_blkfam lib_blkgrp lib_blksub lib_blkpag
			  "("  lib_blkpfx lib_blkfam lib_blkgrp lib_blksub lib_blkpag lib_blkblk ")")
  )
)


;ao selecionar um subgrupo:
;	atualiza a lista de blocos
;	atualiza os slides
;	atualiza as propiedades
(defun net_lib_action_sublist ()
  (net_lib_blk_grayout)
  (setq lib_sublist_key $value
	lib_blkpag "01")
  (if (= 1 (strlen lib_sublist_key)) (setq lib_sublist_key (strcat "0" lib_sublist_key)))
  (setq lib_blksub lib_sublist_key)
  (net_lib_clearimg)
  (net_lib_fillimg)
  (net_lib_fillpag)
  (net_lib_fillgpp)
  (net_lib_nextprev)
  (net_lib_fill_currpage)
  (net_lib_scaleblock)
)

;controla escala de inserção de blocos gráficos
(defun net_lib_scaleblock ()
  (if (= "1" grp_type)
    (progn
      (mode_tile "lib_sclblk_toggle" 1)
      (mode_tile "lib_sclblk_factor" 1)
    )
    (progn
      (mode_tile "lib_sclblk_toggle" 0)
      (mode_tile "lib_sclblk_factor" 0)
    )
  )
)

(defun net_lib_fillgpp ()
  (setq lib_currsgp (strcat cnp_netroot "/slides/" lib_blkpfx lib_blkfam lib_blkgrp lib_blksub ".sgp")
	lib_currsgp_open (open lib_currsgp "r" "utf8")
	grp_type (read-line lib_currsgp_open)
	grp_unit (read-line lib_currsgp_open)
	lib_currsgp_layname (read-line lib_currsgp_open)
	lib_currsgp_laycol (read-line lib_currsgp_open))
  (close lib_currsgp_open)
  (if (= "1" grp_type)
    (setq txpart1 "Tipo = Real ; ")
    (setq txpart1 "Tipo = Gráfico ; ")
  )
  (cond
    ((= "1" grp_unit) (setq txpart2 "Unid. = Metro"))
    ((= "100" grp_unit) (setq txpart2 "Unid. = Centímetro"))
    ((= "1000" grp_unit) (setq txpart2 "Unid. = Milímetro"))
  )
  (set_tile "lib_blktype" (strcat txpart1 txpart2))
  (set_tile "lib_blklayer" (strcat "Layer = " lib_currsgp_layname))
  (start_image "lib_blklaycol")
  (fill_image  0  0
    (dimx_tile "lib_blklaycol")
    (dimy_tile "lib_blklaycol")
    (fix (distof lib_currsgp_laycol))
  )
  (end_image)
)

;ao selecionar um grupo, preenche o subgrupo
(defun net_lib_action_grplist ()
  (setq lib_grplist_key $value)
  (if (= 1 (strlen lib_grplist_key)) (setq lib_grplist_key (strcat "0" lib_grplist_key)))
  (setq lib_blkgrp lib_grplist_key
	lib_blksub "00"
	lib_blkpag "01"
	lib_blkblk "11")
  (net_lib_fillsub)
  (set_tile "lib_sublist" "0")
  (net_lib_clearimg)
  (net_lib_fillimg)
  (net_lib_fillgpp)
  (net_lib_fillpag)
  (net_lib_fill_currpage)
  (net_lib_nextprev)
)

;***************************************************
;botão "Inserir"
;salva o arquivo e insere o bloco
;***************************************************
(defun net_lib_lastlib_insert ()
  (net_lib_save_lastlib)
  (if (not (findfile lib_currdwg))
    (progn
      (cn7_alert_ok 
	"Bloco não encontrado,"
	"ou arquivo corrompido!"
	"Selecione outro ícone...")	
      (net_lib_dcl)
    )
    (progn
      (cn7_find_blkscl)
      ;(cn7_insert_point)
      (if (= lib_inslay "0")
	(cn7_verylayer (strcat cn7_blk_prefixlay lib_currsgp_layname) (fix (distof lib_currsgp_laycol)))
      )
      (if (= lib_blktog "1") (setq cn7_blkscl (* cn7_blkscl (distof lib_blkscl))))
      (prompt "\nSelecione o ponto de inserção e escolha o ângulo de rotação... ")
      (command "._insert" lib_currdwg "_scale" cn7_blkscl)
    )
  )
)

(defun c:net_ru ()
  (if (not (findfile lib_currdwg))
    (progn
      (cn7_alert_ok 
	"Bloco não encontrado,"
	"ou arquivo corrompido!"
	"Selecione outro ícone...")	
      (net_lib_dcl)
    )
    (progn
      (cn7_find_blkscl)
      ;(cn7_insert_point)
      (if (= lib_inslay "0")
	(cn7_verylayer (strcat cn7_blk_prefixlay lib_currsgp_layname) (fix (distof lib_currsgp_laycol)))
      )
      (if (= lib_blktog "1") (setq cn7_blkscl (* cn7_blkscl (distof lib_blkscl))))
      (prompt "\nSelecione o ponto de inserção e escolha o ângulo de rotação... ")
      (command "._insert" lib_currdwg "_scale" cn7_blkscl pause pause)
    )
  )
  (princ)
)
  

(defun net_cn7_insert_point ()
  (initget 128)
  (setq pt1 (getpoint "\nMeio de 2 pontos/<Ponto de inserção...>"))
  (cond
    ((= 'LIST (type pt1))
     (setq pt1 pt1)
     )
    ((= 'STR  (type pt1))
     (cond
       ((or (= "M" (strcase pt1)) (= "2" (strcase pt1)))
	(setq pt2 (getpoint "\nPrimeiro ponto, de dois...")
	      pt3 (getpoint pt2 "\nSegundo ponto, de dois...")
	      pt1 (polar pt2 (angle pt2 pt3) (/ (distance pt2 pt3) 2)))
	)
       (t (prompt "\nOpção inválida! Digite 'M' ou marque o primeiro ponto...")
	(net_cn7_insert_point)
	)
       )
     )
    )
  )





;limpa os slides
(defun net_lib_clearimg ()
  (setq kl "11") (net_lib_upd_icon2)
  (setq kl "12") (net_lib_upd_icon2)
  (setq kl "13") (net_lib_upd_icon2)
  (setq kl "14") (net_lib_upd_icon2)
  (setq kl "21") (net_lib_upd_icon2)
  (setq kl "22") (net_lib_upd_icon2)
  (setq kl "23") (net_lib_upd_icon2)
  (setq kl "24") (net_lib_upd_icon2)
  (setq kl "31") (net_lib_upd_icon2)
  (setq kl "32") (net_lib_upd_icon2)
  (setq kl "33") (net_lib_upd_icon2)
  (setq kl "34") (net_lib_upd_icon2)
  (setq kl "41") (net_lib_upd_icon2)
  (setq kl "42") (net_lib_upd_icon2)
  (setq kl "43") (net_lib_upd_icon2)
  (setq kl "44") (net_lib_upd_icon2)
)

(defun net_lib_upd_icon2 ()
  (setq x (dimx_tile (strcat "icon" kl)) y (dimy_tile (strcat "icon" kl)))
  (start_image (strcat "icon" kl))
  (fill_image 0 0 x y -2)
  (end_image)
)

;preenche os slides
(defun net_lib_fillimg ()
   (setq kl "11") (net_lib_upd_icon)
   (setq kl "12") (net_lib_upd_icon)
   (setq kl "13") (net_lib_upd_icon)
   (setq kl "14") (net_lib_upd_icon)
   (setq kl "21") (net_lib_upd_icon)
   (setq kl "22") (net_lib_upd_icon)
   (setq kl "23") (net_lib_upd_icon)
   (setq kl "24") (net_lib_upd_icon)
   (setq kl "31") (net_lib_upd_icon)
   (setq kl "32") (net_lib_upd_icon)
   (setq kl "33") (net_lib_upd_icon)
   (setq kl "34") (net_lib_upd_icon)
   (setq kl "41") (net_lib_upd_icon)
   (setq kl "42") (net_lib_upd_icon)
   (setq kl "43") (net_lib_upd_icon)
   (setq kl "44") (net_lib_upd_icon)
)

(defun net_lib_upd_icon ()
   (setq curr_icon (strcat cnp_netroot "/slides/" lib_blkpfx lib_blkfam lib_blkgrp lib_blksub lib_blkpag
			   "("  lib_blkpfx lib_blkfam lib_blkgrp lib_blksub lib_blkpag kl ")"))
   (setq x (dimx_tile (strcat "icon" kl)) y (dimy_tile (strcat "icon" kl)))
   (start_image (strcat "icon" kl))
   (slide_image 0 0 x y curr_icon)
   (end_image)
)


;preenche a listagem de grupos (último utilizado)
(defun net_lib_fillgrp ()
  (setq lib_grplist (list))
  (setq open_file (open (strcat cnp_netroot "/slides/" lib_blkpfx lib_blkfam ".txt") "r" "utf8"))
  ;cada linha contém nome;prefixo do grupo
  (while (/= nil (setq linha (read-line open_file)))
    (setq lib_grplist (append lib_grplist (list linha)))
  )
  (close open_file)
  (start_list "lib_grplist")
  (mapcar 'add_list lib_grplist)
  (end_list)
)

;preenche a listagem de sub-grupos (último utilizado)
(defun net_lib_fillsub ()
  (setq lib_sublist (list))
  (setq open_file (open (strcat cnp_netroot "/slides/" lib_blkpfx lib_blkfam lib_blkgrp ".txt") "r" "utf8"))
  (while (/= nil (setq linha (read-line open_file)))
    (setq lib_sublist (append lib_sublist (list linha)))
  )
  (close open_file)
  (start_list "lib_sublist")
  (mapcar 'add_list lib_sublist)
  (end_list)
)

;preenche a listagem de página (última utilizado)
(defun net_lib_fillpag ()
  (setq lib_paglist (list))
  (setq open_file (open (strcat cnp_netroot "/slides/" lib_blkpfx lib_blkfam lib_blkgrp lib_blksub lib_blkpag ".txt") "r" "utf8"))
  (while (/= nil (setq linha (read-line open_file)))
    (setq lib_paglist (append lib_paglist (list linha)))
  )
  (close open_file)
  (start_list "lib_paglist")
  (mapcar 'add_list lib_paglist)
  (end_list)
)

;guarda os valores da última biblioteca acessada
(defun net_lib_save_lastlib ()
  (setq file2 (open (strcat cnp_root "/config/lastlib.txt") "w" "utf8"))
  (write-line lib_blkgrp file2)
  (write-line lib_blksub file2)
  (write-line lib_blkpag file2)
  (write-line lib_blkblk file2)
  (write-line lib_blkscl file2)
  (close file2)
)

;***************************************************************
;	Gerenciador de Grupos					
;***************************************************************
(defun c:net_grp ()
  (if (not lib_blkfam) (setq lib_blkfam "aq"))
  (net_lib_manager)
  (princ)
)


;deniog
;abre e gerencia DCL
(defun net_lib_manager ()
  (setq dcl_id (load_dialog (strcat cnp_root "/lisp/cadnorma.dcl")))
  (if (not (new_dialog "lib_grpmanager" dcl_id)) (exit))
  (net_lib_mng_label)
  (net_lib_fillgrp)
  (net_lib_fillsub)
  (net_grp_buttons_off)
  (action_tile "lib_grplist" "(net_grp_grplist_action)")
  (action_tile "lib_sublist" "(net_grp_sublist_action)")
  (action_tile "sub_chtype" "(net_grp_sub_changetype)")
  (action_tile "sub_chunit" "(net_grp_sub_changeunit)")
  (action_tile "sub_chlayn" "(net_grp_sub_changenlay)")
  (action_tile "grp_sub_rename" "(net_grp_sub_rename)")
  (action_tile "cancel" "(done_dialog 0)")
  (action_tile "accept" "(done_dialog 1)")
  (action_tile "grp_grprename" "(done_dialog 2)")
  (action_tile "grp_grpnew" "(done_dialog 3)")
  (action_tile "grp_sub_page" "(done_dialog 4)")
  (action_tile "grp_sub_new" "(done_dialog 5)")
  (setq grpdcl_dialog (start_dialog))
  (unload_dialog dcl_id)
  (if (= 1 grpdcl_dialog) (net_lib_cfgmain_lib))
  (if (= 2 grpdcl_dialog) (net_grp_grprename_action))
  (if (= 3 grpdcl_dialog) (net_grp_grpnew_action))
  (if (= 4 grpdcl_dialog) (net_grp_grpmore_action))
  (if (= 5 grpdcl_dialog) (net_grp_grpnewsub_action))
)



;criar novo subgrupo
(defun net_grp_grpnewsub_action () (cnp:unsupported "net_grp_grpnewsub_action"))


      
;aumentar capacidade do subgrupo (criar nova página)
(defun net_grp_grpmore_action () (cnp:unsupported "net_grp_grpmore_action"))

;renomear subgrupo
(defun net_grp_sub_rename ()
  (setq sgp_chsubname_newname nil)
  (setq dcl_id (load_dialog (strcat cnp_root "/lisp/cadnorma.dcl")))
  (if (not (new_dialog "grp_sub_rename" dcl_id)) (exit))
  (set_tile "sub_chsubname_edit" (nth (read lib_blksub) lib_sublist))
  (mode_tile "sub_chsubname_edit" 2)
  (action_tile "sub_chsubname_edit" "(setq sgp_chsubname_newname $value)")
  (action_tile "cancel" "(done_dialog 0)")
  (action_tile "accept" "(done_dialog 1)")
  (setq sub_rename_dialog (start_dialog))
  (unload_dialog dcl_id)
  (if (= 1 sub_rename_dialog)
    (if (and (/= nil sgp_chsubname_newname) (/= "" sgp_chsubname_newname))
      (progn
	(setq n_ordem (read lib_blksub)
	      list_n (length lib_sublist)
	      counter 0
	      new_list (list "")
	)
	(repeat list_n
	  (if (= counter n_ordem)
	    (setq new_list (append new_list (list sgp_chsubname_newname)))
	    (setq new_list (append new_list (list (nth counter lib_sublist))))
	  )
	  (setq counter (1+ counter))
	);repeat
	(setq lib_sublist (cdr new_list))
	(setq open_file (open (strcat cnp_netroot "/slides/" lib_blkpfx lib_blkfam lib_blkgrp ".txt") "w" "utf8"))
	(foreach n lib_sublist
	  (write-line n open_file)
	)
	(close open_file)
	(net_lib_fillsub)
	(start_list "lib_sublist")
	(mapcar 'add_list lib_sublist)
	(end_list)
	(net_grp_buttons_off)
      )
    )
  )	      
)

;altera o layer de inserção do bloco
(defun net_grp_sub_changenlay ()
  (net_grp_sub_readprop)
  (setq sgp_chlayer_newlayer nil)
  (setq dcl_id (load_dialog (strcat cnp_root "/lisp/cadnorma.dcl")))
  (if (not (new_dialog "grp_sub_change_layer" dcl_id)) (exit))
  (set_tile "sub_chlayer_edit" sgp_sublayn)
  (action_tile "sub_chlayer_edit" "(setq sgp_chlayer_newlayer $value)")
  (mode_tile "sub_chlayer_edit" 2)
  (action_tile "cancel" "(done_dialog 0)")
  (action_tile "accept" "(done_dialog 1)")
  (setq sub_changelayer_dialog (start_dialog))
  (unload_dialog dcl_id)
  (if (= 1 sub_changelayer_dialog)
    (if (and (/= nil sgp_chlayer_newlayer) (/= "" sgp_chlayer_newlayer))
      (progn
	(setq sgp_sublayn sgp_chlayer_newlayer)
	(set_tile "lib_blklayer" sgp_chlayer_newlayer)
	(net_grp_sgp_resave)
      )
    )
  )
)

;altera a unidade do bloco
(defun net_grp_sub_changeunit ()
  (setq sgp_chunit_newunit nil)
  (setq dcl_id (load_dialog (strcat cnp_root "/lisp/cadnorma.dcl")))
  (if (not (new_dialog "grp_sub_change_unit" dcl_id)) (exit))
  (cond
    ((= sgp_subunit "1") (set_tile "sgp_chunit_radio" "sub_chunit_0"))
    ((= sgp_subunit "100") (set_tile "sgp_chunit_radio" "sub_chunit_1"))
    ((= sgp_subunit "1000") (set_tile "sgp_chunit_radio" "sub_chunit_2"))
  )
  (action_tile "sgp_chunit_radio" "(setq sgp_chunit_newunit $value)")
  (action_tile "accept" "(done_dialog 1)")
  (action_tile "cancel" "(done_dialog 0)")
  (setq sub_changeunit_dialog (start_dialog))
  (unload_dialog dcl_id)
  (if (= 1 sub_changeunit_dialog);se clica em 'ok' 
    (progn
      (if (/= nil sgp_chunit_newunit);se algum tipo foi clicado
	(progn
	  (cond
	    ((= sgp_chunit_newunit "sub_chunit_0") (setq sgp_subunit "1") (set_tile "lib_blkunit" "Unidade: Metros"))
	    ((= sgp_chunit_newunit "sub_chunit_1") (setq sgp_subunit "100") (set_tile "lib_blkunit" "Unidade: Centímetros"))
	    ((= sgp_chunit_newunit "sub_chunit_2") (setq sgp_subunit "1000") (set_tile "lib_blkunit" "Unidade: Milímetros"))
	  )	  	    
	  (net_grp_sgp_resave)
	)
      )
    )
  )
)

;altera o tipo de subgrupo
(defun net_grp_sub_changetype ()
  (setq sgp_chtype_newtype nil)
  (setq dcl_id (load_dialog (strcat cnp_root "/lisp/cadnorma.dcl")))
  (if (not (new_dialog "grp_sub_change_type" dcl_id)) (exit))
  (if (= sgp_subtype "1")
    (set_tile "sgp_chtype_radio" "sub_chtype_1")
    (set_tile "sgp_chtype_radio" "sub_chtype_2")
  )
  (action_tile "sgp_chtype_radio" "(setq sgp_chtype_newtype $value)")
  (action_tile "accept" "(done_dialog 1)")
  (action_tile "cancel" "(done_dialog 0)")
  (setq sub_changetype_dialog (start_dialog))
  (unload_dialog dcl_id)
  (if (= 1 sub_changetype_dialog);se clica em 'ok' 
    (progn
      (if (/= nil sgp_chtype_newtype);se algum tipo foi clicado
	(progn
	  (if (= sgp_chtype_newtype "sub_chtype_1")
	    (progn
	      (setq sgp_subtype "1")
	      (set_tile "lib_blktype" "Tipo: Reais")
	      (mode_tile "lib_blkunit" 0)
	      (mode_tile "sub_chunit" 0)
	    )
	    (progn
	      (setq sgp_subtype "2")
	      (set_tile "lib_blktype" "Tipo: Gráficos")
	      (mode_tile "lib_blkunit" 1)
	      (mode_tile "sub_chunit" 1)
	      (setq sgp_subunit "100")
	      (set_tile "lib_blkunit" "Unidade: Centímetros")
	    )
	  )	    
	  (net_grp_sgp_resave)
	)
      )
    )
  )      
)


;altera a cor do layer do subgrupo
(defun net_grp_sub_changecol ()
  (net_grp_sub_readprop)
  (setq new_color (acad_colordlg (fix (distof sgp_sublayc))))
  (if (/= nil new_color)
    (progn
      (setq sgp_sublayc (rtos new_color 2 0))
      (net_grp_sgp_resave)
      (start_image "lib_blklaycol")
      (fill_image  0  0
	(dimx_tile "lib_blklaycol")
	(dimy_tile "lib_blklaycol")
	(fix (distof sgp_sublayc))
	)
      (end_image)
    )
  )
)

;salva o arquivo de sub_propriedades, quando uma delas é alterada
(defun net_grp_sgp_resave ()
  (setq sub_ppdfile (strcat cnp_netroot "/slides/" lib_blkpfx lib_blkfam lib_blkgrp lib_blksub ".sgp")
	open_file (open sub_ppdfile "w" "utf8"))
  (write-line sgp_subtype open_file)
  (write-line sgp_subunit open_file)
  (write-line sgp_sublayn open_file)
  (write-line sgp_sublayc open_file)
  (close open_file)
)


;ao selecionar um subgrupo
(defun net_grp_sublist_action ()
  (setq grp_sublist_key $value)
  (if (= 1 (strlen grp_sublist_key)) (setq grp_sublist_key (strcat "0" grp_sublist_key)))
  (setq lib_blksub grp_sublist_key)
  (net_grp_sub_buttons_on)
  (net_grp_sub_readprop)
  (action_tile "lib_blklaycol" "(net_grp_sub_changecol)")
)

;ao selecionar um grupo, limpa as propriedades de subgrupo
(defun net_grp_sub_clearsgp ()
  (set_tile "lib_blktype" "")
  (set_tile "lib_blkunit" "")
  (set_tile "lib_blklayer" "")
  (start_image "lib_blklaycol")
  (fill_image  0  0
    (dimx_tile "lib_blklaycol")
    (dimy_tile "lib_blklaycol")
  -2)
  (end_image)
  (net_grp_buttons_off)
)
  
;lê as ropriedades do subgrupo selecionado
(defun net_grp_sub_readprop ()
  (setq sub_ppdfile (strcat cnp_netroot "/slides/" lib_blkpfx lib_blkfam lib_blkgrp lib_blksub ".sgp")
	open_file (open sub_ppdfile "r" "utf8")
	sgp_subtype (read-line open_file)
	sgp_subunit (read-line open_file)
	sgp_sublayn (read-line open_file)
	sgp_sublayc (read-line open_file)
  )
  (close open_file)
  (if (= sgp_subtype "1")
   (set_tile "lib_blktype" "Tipo: Reais")
   (progn
      (set_tile "lib_blktype" "Tipo: Gráficos")
      (set_tile "lib_blkunit" "Unidade: Centímetros")
      (mode_tile "lib_blkunit" 1)
      (mode_tile "sub_chunit" 1)
    )
  )
  (cond
    ((= sgp_subunit "1") (set_tile "lib_blkunit" "Unidade: Metros") (setq grp_unit "1"))
    ((= sgp_subunit "100") (set_tile "lib_blkunit" "Unidade: Centímetros") (setq grp_unit "100"))
    ((= sgp_subunit "1000") (set_tile "lib_blkunit" "Unidade: Milímetros") (setq grp_unit "1000"))
  )
  (set_tile "lib_blklayer" sgp_sublayn)
  (start_image "lib_blklaycol")
  (fill_image  0  0
    (dimx_tile "lib_blklaycol")
    (dimy_tile "lib_blklaycol")
    (fix (distof sgp_sublayc))
  )
  (end_image)
)
	

;grayon dos botões e grupos
(defun net_grp_sub_buttons_on ()
  (mode_tile "lib_sub_propbox" 0)
  (mode_tile "lib_sub_laybox" 0)
  (mode_tile "grp_sub_rename" 0)
  (mode_tile "grp_sub_new" 0)
  (mode_tile "grp_sub_prop" 0)
  (mode_tile "grp_sub_page" 0)
)


;botão Novo Grupo
(defun net_grp_grpnew_action () (cnp:unsupported "net_grp_grpnew_action"))

;nome do novo grupo
(defun net_grp_grpnew_getname ()
  (setq next_group (rtos (length lib_grplist) 2 0))
  (if (= 1 (strlen next_group)) (setq next_group (strcat "0" next_group)))
  (setq old_name (strcat "Grupo " next_group)
	new_name old_name)
  (setq dcl_id (load_dialog (strcat cnp_root "/lisp/cadnorma.dcl")))
  (if (not (new_dialog "grp_grprename_dcl" dcl_id)) (exit))
  (set_tile "grp_grprename_edit" old_name)
  (action_tile "grp_grprename_edit" "(setq new_name $value)")
  (mode_tile "grp_grprename_edit" 2)
  (action_tile "accept" "(done_dialog 1)")
  (action_tile "cancel" "(done_dialog 0)")
  (setq grp_grprename_dialog (start_dialog))
  (unload_dialog dcl_id)
  (if (= 0 grp_grprename_dialog) (exit))
  (if (= 1 grp_grprename_dialog) (net_grp_grpnew_getname_ok))
)


;botão ok -> salva nome novo
(defun net_grp_grpnew_getname_ok ()
  (setq open_file (open (strcat cnp_netroot "/slides/" lib_blkpfx lib_blkfam ".txt") "r" "utf8")
	new_list (list ""))
  (while (/= nil (setq linha (read-line open_file)))
    (setq new_list (append new_list (list linha)))
  )
  (close open_file)
  (setq new_list (append new_list (list new_name))
	new_list (cdr new_list))
  (setq open_file (open (strcat cnp_netroot "/slides/" lib_blkpfx lib_blkfam ".txt") "w" "utf8"))
  (foreach n new_list
    (write-line n open_file)
  )
  (close open_file)
)
  
;botão Renomear Grupo
(defun net_grp_grprename_action ()
  (setq ordem (read lib_blkgrp)
	old_name (nth ordem lib_grplist)
	new_name old_name)
  (setq dcl_id (load_dialog (strcat cnp_root "/lisp/cadnorma.dcl")))
  (if (not (new_dialog "grp_grprename_dcl" dcl_id)) (exit))
  (set_tile "grp_grprename_edit" old_name)
  (action_tile "grp_grprename_edit" "(setq new_name $value)")
  (mode_tile "grp_grprename_edit" 2)
  (action_tile "accept" "(done_dialog 1)")
  (action_tile "cancel" "(done_dialog 0)")
  (setq grp_grprename_dialog (start_dialog))
  (unload_dialog dcl_id)
  (if (= 1 grp_grprename_dialog) (net_grp_grprename_action_ok))
)

;botão ok -> salva nome novo
(defun net_grp_grprename_action_ok ()
  (setq cont 0 new_list (list ""))
  (foreach n lib_grplist
    (if (= cont ordem)
      (setq new_list (append new_list (list new_name)))
      (setq new_list (append new_list (list (nth cont lib_grplist))))
    )
    (setq cont (1+ cont))
  )
  (setq lib_grplist (cdr new_list))
  (setq open_file (open (strcat cnp_netroot "/slides/" lib_blkpfx lib_blkfam ".txt") "w" "utf8"))
  (foreach n lib_grplist
    (write-line n open_file)
  )
  (close open_file)
  (net_lib_manager)
)


;grayout dos botões
(defun net_grp_buttons_off ()
  (mode_tile "grp_grprename" 1)
  (mode_tile "grp_sub_rename" 1)
;;;  (mode_tile "grp_sub_new" 1)
  (mode_tile "grp_sub_prop" 1)
  (mode_tile "grp_sub_page" 1)
  (mode_tile "lib_sub_propbox" 1)
  (mode_tile "lib_sub_laybox" 1)
)

;ao selecionar um grupo, preenche o subgrupo
(defun net_grp_grplist_action ()
  (setq grp_grplist_key $value)
  (if (= 1 (strlen grp_grplist_key)) (setq grp_grplist_key (strcat "0" grp_grplist_key)))
  (setq lib_blkgrp grp_grplist_key)
  (net_lib_fillsub)
  (net_grp_sub_clearsgp)
  (mode_tile "grp_grprename" 0)
  (mode_tile "grp_grpnew" 0)
)


;***************************************************************************************
;**************** Biblioteca de Fabricantes Credenciados Cadnorma **********************
;***************************************************************************************
(defun c:bib () (bib_main) (princ))

;inicializa o gerenciador de blocos de fabricantes
(defun bib_main ()
  (setq lib_list (list))
  (setq file (open (strcat cnp_root "/fabricantes/fablib.txt") "r" "utf8"))
  (while (/= nil (setq linha (read-line file)))
    (setq lib_list (append lib_list (list linha)))
  )
  (close file)
  (setq dcl_id (load_dialog (strcat cnp_root "/lisp/cadnorma.dcl")))
  (if (not (new_dialog "cn8_lib" dcl_id)) (exit))
  (start_list "lib_grupos")
  (mapcar 'add_list lib_list)
  (end_list)
  (mode_tile "cn8_lib_btn_use" 1)
  (mode_tile "cn8_lib_btn_www" 1)
  (mode_tile "accept" 1)
  (action_tile "lib_grupos" "(cnlib_updinfo)")
  (action_tile "cancel" "(done_dialog 0)")
  (action_tile "accept" "(done_dialog 2)")
  (action_tile  "cn8_lib_btn_add" "(done_dialog 3)")
  (action_tile  "cn8_lib_btn_www" "(done_dialog 4)")
;;;  (action_tile  "cn8_lib_btn_rmv" "(done_dialog 5)")
  (setq fablib_dialog (start_dialog))
  (unload_dialog dcl_id)
  (cond
    ((= 2 fablib_dialog) (cn8_lib_use))
    ((= 3 fablib_dialog) (cn8_lib_add))
    ((= 4 fablib_dialog) (cn8_lib_www))
  )
)


;acessa o site do fabricante
(defun cn8_lib_www ()
  (command "._browser" cn8_site)
)


;adiciona um item à biblioteca
(defun cn8_lib_add ()
  (setq arq1 (getfiled "Selecione uma nova biblioteca" (strcat cnp_root "/fabricantes/") "cnl" 8))
  (setq open_file (open arq1 "r" "utf8"))
  (repeat 6 (setq linha (read-line open_file)))
  (setq cn8_lib_access (read-line open_file))
  (close open_file)
  (setq lib_list (list))
  (setq arq2 (open (strcat cnp_root "/fabricantes/fablib.txt") "r" "utf8"))
  (while (/= nil (setq linha (read-line arq2)))
    (if (/= cn8_lib_access linha)
      (setq lib_list (append (list linha) lib_list))
      (progn
	(cn7_alert_ok
	  "Esta Biblioteca já está"
	  "Instalada em seu computador"
	  "Impossível instalar novamente..."
	)
	(close arq2)
	(exit)
      )
    )
  )
  (close arq2)
  (setq lib_list (append lib_list (list cn8_lib_access)))
  (setq arq3 (open (strcat cnp_root "/fabricantes/fablib.txt") "w" "utf8"))
  (foreach n lib_list
    (write-line n arq3)
  )
  (close arq3)
;;;  (cn8_libload)
  (bib_main)
)


;acessar a bilioteca escolhida
(defun cn8_lib_use ()
  (load (strcat cnp_root "/fabricantes/" cn8_lib_access ".lsp"))
)

;ao selecionar um grupo, preenche os dados
(defun cnlib_updinfo ()
  (setq n $value)
  (mode_tile "cn8_lib_btn_use" 0)
  (mode_tile "cn8_lib_btn_www" 0)
  (mode_tile "accept" 0)
  (setq file (strcat cnp_root "/fabricantes/" (nth (fix (distof n)) lib_list) ".cnl"))
  (setq open_file (open file "r" "utf8"))
  (set_tile "fablib_txt1" (read-line open_file))
  (setq cn8_site (read-line open_file))
  (set_tile "fablib_txt2" cn8_site)
  (set_tile "fablib_txt3" (read-line open_file))
  (set_tile "fablib_txt4" (strcat "   " (read-line open_file)))
  (set_tile "fablib_txt5" (strcat "   " (read-line open_file)))
  (set_tile "fablib_txt6" (strcat "   " (read-line open_file)))
  (setq cn8_lib_access (read-line open_file))
  (set_tile "fablib_txt7" (strcat "Comando de acesso: " cn8_lib_access))
  (close open_file)
)


;cnp_21_a

;*******************************************
;desnível de piso
;*******************************************
(defun c:dsnv ()
  (guarda '("blipmode" "cecolor" "celtype" "clayer" "cmdecho" "orthomode"
          "textstyle" "luprec" "osmode" ))
  (setvar "cmdecho" 0)
  (setq attmode (getvar "attdia"))
  (setvar "attdia"  0)
  (setq pt1 (getpoint "\nIndique o ponto do desnivel...")
	pt2 (getpoint pt1 "\nClique no lado mais alto...")
	rang (angle pt1 pt2)
	pt3 (polar pt1 (angle pt2 pt1) (distance pt2 pt1)))
  (setq altd (getstring "\nAltura do desnivel (em cm)? "))
  (setq grp_type "2")
  (cn7_find_blkscl)
  (cn7_verylayer (strcat cn7_blk_prefixlay "Desnível") 1)
  (if (or
	(and (>= rang 0) (<= rang (/ pi 2)))
	(and (>= rang (/ (* pi 3) 2)) (<= rang (* 2 pi))))
    (command "._insert" (strcat cnp_root "/blocos/dsnv1") "_non" pt1 cn7_blkscl "" pt2 altd)
    (command "._insert" (strcat cnp_root "/blocos/dsnv2") "_non" pt1 cn7_blkscl "" pt3 altd)
  )
  (devolve)
  (setvar "attdia"  attmode)
)

;*******************************************
;indicação de escada que sobe
;*******************************************
(defun c:sobe ()
  (guarda '("blipmode" "cecolor" "celtype" "clayer" "cmdecho" "orthomode"
          "textstyle" "luprec" "osmode" ))
  (setvar "cmdecho" 0)
  (setq grp_type "2" grp_unit "100")
  (cn7_find_blkscl)
  (cn7_verylayer (strcat cn7_blk_prefixlay "Escada_sobe") 1)
  (setq pt1 (getpoint  "\nInício da subida......"))
  (setq psimb_txt pt1)
  (command "._insert" (strcat cnp_root "/blocos/escada_sobe") "_scale" cn7_blkscl "_non" pt1 "0" "._pline" "_non" "@")
  (while (/= nil (setq pt2 (getpoint pt1 "\nPróximo ponto...")))
    (setq ang (+ 180 (* 180 (/ (angle pt1 pt2) pi))))
    (command pt2)
    (setq pt1 pt2)
  )
  (command "" "insert" (strcat cnp_root "/blocos/util_st1") "_scale" cn7_blkscl "_non" "@" ang)
  (setq psimb_txt (getpoint psimb_txt "\nPosição do texto..."))
  (initget "Sobe Desce")
  (setq sobe_opt (getkword "Desce/<Sobe>: "))
  (if (= sobe_opt nil) (setq sobe_opt "Sobe"))
  (if (= sobe_opt "Sobe")
    (cn7_txsimb "r60" "_m" "S" 1 (strcat cn7_blk_prefixlay "Escada_sobe") 0)
    (cn7_txsimb "r60" "_m" "D" 1 (strcat cn7_blk_prefixlay "Escada_sobe") 0)
  )
  (devolve)
  (setq grp_type nil)
  (princ)
)







;cnp_21_b

;*********************************************
;Cadnorma Professional                        
;Gerador de Coberturas                        
;                                             
;Iniciado em 23/02/11                         
;por Denio Guimarães                          
;*********************************************
(defun c:cbt ()
	(cbt_last_file)
	(cbt_main)
)

;função principal - DCL de Dados
(defun cbt_main ()
  (cn7_init)
  ;abre a caixa de diálogo
  (setq dcl_id (load_dialog (strcat cnp_root "/lisp/cadnorma.dcl")))
  (if (not (new_dialog "coberturas" dcl_id)) (exit))
  (cbt_update_slides)
  ;atualiza o texto
  (cond
    ((= cbt_var_tipo "11") (set_tile "cbt_text_type" "Tipo Atual: Uma Água"))
    ((= cbt_var_tipo "12") (set_tile "cbt_text_type" "Tipo Atual: Duas Águas"))
    ((= cbt_var_tipo "13") (set_tile "cbt_text_type" "Tipo Atual: Três Águas"))
    ((= cbt_var_tipo "21") (set_tile "cbt_text_type" "Tipo Atual: Quatro Águas"))
    ((= cbt_var_tipo "22") (set_tile "cbt_text_type" "Tipo Atual: Seis Águas e 'L'"))
    ((= cbt_var_tipo "23") (set_tile "cbt_text_type" "Tipo Atual: Sete Águas em 'T'"))
  )
  ;hachuras
  (set_tile "cbt_tog_hch" cbt_var_dhch)
  (cbt_eval_hatch)
  (action_tile "cbt_tog_hch" "(cbt_hchtog_action)")
  (setq cbt_hch_list (list "ANSI" "TELHA 01" "TELHA 02" "TELHA 03" "TELHA 04"
			   "TELHA 05" "TELHA 06" "TELHA 07" )
  )
  (start_list "cbt_lst_hch")
  (mapcar 'add_list cbt_hch_list)
  (end_list)
  (set_tile "cbt_lst_hch" cbt_var_thch)
  (action_tile "cbt_lst_hch" "(cbt_lst_hchaction)")
  (cbt_upd_imghch)
  ;fator da hachura
  (set_tile "cbt_fat_hch" cbt_var_fhch)
  (action_tile "cbt_fat_hch" "(cb1_drw_evalfhch)")
  ;seta de caimento
  (set_tile "cbt_tog_set" cbt_var_dset)
  (cbt_eval_seta)
  (action_tile "cbt_tog_set" "(cbt_settog_action)")
  (setq cbt_set_list (list "SETA 01" "SETA 02" "SETA 03" "SETA 04"))
  (start_list "cbt_lst_set")
  (mapcar 'add_list cbt_set_list)
  (end_list)
  (set_tile "cbt_lst_set" cbt_var_tset)
  (action_tile "cbt_lst_set" "(cbt_lst_setaction)")
  (cbt_upd_imgset)
  ;fator da seta
  (set_tile "cbt_fat_set" cbt_var_fset)
  (action_tile "cbt_fat_set" "(cb1_drw_evalfset)")
  ;configuração de cores e layers
  (action_tile "cbt_cfg_laycol" "(done_dialog 2)")
  ;funções ok_cancel
  (action_tile "cancel" "(done_dialog 0)")
  (action_tile "accept" "(done_dialog 1)")
  ;ativação da DCL
  (setq cbt_dcl_id (start_dialog))
  (unload_dialog dcl_id)
  ;ações dos botões
  (if (= 1 cbt_dcl_id) (cbt_ok_action))
  (if (= 2 cbt_dcl_id) (cbt_laycol_button))
  (princ)
)

;*****************************************
;Botão OK                                 
;*****************************************


;ao clicar no botão "ok"
(defun cbt_ok_action ()
  (cbt_last_writefile)
  (cbt_getdata)
)

;avalia se o fator entrado é válido para fator de seta
(defun cb1_drw_evalfset ()
  (setq cbt_var_newfset $value)
  (if (distof cbt_var_newfset)
    (setq cbt_var_fset cbt_var_newfset)
    (progn
      (alert "Valor Inválido!\nDigite um número Real.")
      (set_tile "cbt_fat_set" cbt_var_fset)
      (mode_tile "cbt_fat_set" 2)
    )
  )
)

;avalia se o fator entrado é válido para fator de hachura
(defun cb1_drw_evalfhch ()
  (setq cbt_var_newfhch $value)
  (if (distof cbt_var_newfhch)
    (setq cbt_var_fhch cbt_var_newfhch)
    (progn
      (alert "Valor Inválido!\nDigite um número Real.")
      (set_tile "cbt_fat_hch" cbt_var_fhch)
      (mode_tile "cbt_fat_hch" 2)
    )
  )
)  



;***********************************
;Configuração de Cores e Layers     
;***********************************
(defun cbt_laycol_button ()
  (cbt_layc_file)
  (setq dcl_id (load_dialog (strcat cnp_root "/lisp/cadnorma.dcl")))
  (if (not (new_dialog "cbt_cfglayc" dcl_id)) (exit))
  ;cobertura
  (set_tile "cbt_layc_cbl" cbt_layc_cbl)
  (action_tile "cbt_layc_cbl" "(setq cbt_layc_cbl $value)")
  (start_image "cbt_layc_cbc")
  (fill_image  0  0
    (dimx_tile "cbt_layc_cbc")
    (dimy_tile "cbt_layc_cbc")
    (fix (distof cbt_layc_cbc))
  )
  (end_image)
  (action_tile "cbt_layc_cbc" "(cbt_layc_cbc_color)")
  ;Vista
  (set_tile "cbt_layc_edl" cbt_layc_edl)
  (action_tile "cbt_layc_edl" "(setq cbt_layc_edl $value)")
  (start_image "cbt_layc_edc")
  (fill_image  0  0
    (dimx_tile "cbt_layc_edc")
    (dimy_tile "cbt_layc_edc")
    (fix (distof cbt_layc_edc))
  )
  (end_image)
  (action_tile "cbt_layc_edc" "(cbt_layc_edc_color)")
  ;Projeção
  (set_tile "cbt_layc_hcl" cbt_layc_hcl)
  (action_tile "cbt_layc_hcl" "(setq cbt_layc_hcl $value)")
  (start_image "cbt_layc_hcc")
  (fill_image  0  0
    (dimx_tile "cbt_layc_hcc")
    (dimy_tile "cbt_layc_hcc")
    (fix (distof cbt_layc_hcc))
  )
  (end_image)
  (action_tile "cbt_layc_hcc" "(cbt_layc_hcc_color)")
  ;Parapeito
  (set_tile "cbt_layc_stl" cbt_layc_stl)
  (action_tile "cbt_layc_stl" "(setq cbt_layc_stl $value)")
  (start_image "cbt_layc_stc")
  (fill_image  0  0
    (dimx_tile "cbt_layc_stc")
    (dimy_tile "cbt_layc_stc")
    (fix (distof cbt_layc_stc))
  )
  (end_image)
  (action_tile "cbt_layc_stc" "(cbt_layc_stc_color)")
  ;ok_cancel
  (action_tile "cancel" "(done_dialog 0)")
  (action_tile "accept" "(done_dialog 1)")
  ;start_dialog
  (setq cbt_layc_id (start_dialog))
  (unload_dialog dcl_id)
  (if (= cbt_layc_id 1)
    (progn
      (cbt_layc_writefile)
      (cbt_main)
    )
  )
  (if (= cbt_layc_id 0) (cbt_main))
)

;escolher cor da Projeção
(defun cbt_layc_hcc_color ()
  (setq cbt_layc_hcc_newcol (acad_colordlg (fix (distof cbt_layc_hcc))))
  (if (/= nil cbt_layc_hcc_newcol) (setq cbt_layc_hcc (rtos cbt_layc_hcc_newcol 2 0)))
  (start_image "cbt_layc_hcc")
  (fill_image  0  0
    (dimx_tile "cbt_layc_hcc")
    (dimy_tile "cbt_layc_hcc")
    (fix (distof cbt_layc_hcc))
  )
  (end_image)
)


;escolher cor da janela em vista
(defun cbt_layc_edc_color ()
  (setq cbt_layc_edc_newcol (acad_colordlg (fix (distof cbt_layc_edc))))
  (if (/= nil cbt_layc_edc_newcol) (setq cbt_layc_edc (rtos cbt_layc_edc_newcol 2 0)))
  (start_image "cbt_layc_edc")
  (fill_image  0  0
    (dimx_tile "cbt_layc_edc")
    (dimy_tile "cbt_layc_edc")
    (fix (distof cbt_layc_edc))
  )
  (end_image)
)

;escolher cor do caixilho
(defun cbt_layc_cbc_color ()
  (setq cbt_layc_cbc_newcol (acad_colordlg (fix (distof cbt_layc_cbc))))
  (if (/= nil cbt_layc_cbc_newcol) (setq cbt_layc_cbc (rtos cbt_layc_cbc_newcol 2 0)))
  (start_image "cbt_layc_cbc")
  (fill_image  0  0
    (dimx_tile "cbt_layc_cbc")
    (dimy_tile "cbt_layc_cbc")
    (fix (distof cbt_layc_cbc))
  )
  (end_image)
)


;escolher cor do parapeito
(defun cbt_layc_stc_color ()
  (setq cbt_layc_stc_newcol (acad_colordlg (fix (distof cbt_layc_stc))))
  (if (/= nil cbt_layc_stc_newcol) (setq cbt_layc_stc (rtos cbt_layc_stc_newcol 2 0)))
  (start_image "cbt_layc_stc")
  (fill_image  0  0
    (dimx_tile "cbt_layc_stc")
    (dimy_tile "cbt_layc_stc")
    (fix (distof cbt_layc_stc))
  )
  (end_image)
)


;lê os dados iniciais da DCL no arquivo de dados
(defun cbt_layc_file ()
  (if (findfile (strcat cnp_root "/config/cbt_layc.txt"))
    (cbt_layc_readfile)
    (progn
      (setq file (open (strcat cnp_root "/config/cbt_layc.txt") "w" "utf8"))
      (write-line "Cobertura" file)
      (write-line "4" file)
      (write-line "Cobertura" file)
      (write-line "2" file)
      (write-line "Cobertura" file)
      (write-line "1" file)
      (write-line "Cobertura" file)
      (write-line "3" file)
      (close file)
      (cbt_layc_readfile)
    )
  )
)

;função que lê o arquivo de dados
(defun cbt_layc_readfile ()
  (setq	file (open (strcat cnp_root "/config/cbt_layc.txt") "r" "utf8"))
  (setq	cbt_layc_cbl (read-line file))
  (setq	cbt_layc_cbc (read-line file))
  (setq	cbt_layc_edl (read-line file))
  (setq	cbt_layc_edc (read-line file))
  (setq	cbt_layc_hcl (read-line file))
  (setq	cbt_layc_hcc (read-line file))
  (setq	cbt_layc_stl (read-line file))
  (setq	cbt_layc_stc (read-line file))
  (close file)
)

;função que escreve o arquivo de dados
(defun cbt_layc_writefile ()
  (setq	file (open (strcat cnp_root "/config/cbt_layc.txt") "w" "utf8"))
  (write-line cbt_layc_cbl file)
  (write-line cbt_layc_cbc file)
  (write-line cbt_layc_edl file)
  (write-line cbt_layc_edc file)
  (write-line cbt_layc_hcl file)
  (write-line cbt_layc_hcc file)
  (write-line cbt_layc_stl file)
  (write-line cbt_layc_stc file)
  (close file)
)


;*********************************
;Setas                            
;*********************************

;ao selecionar uma hachura na lista
(defun cbt_lst_setaction ()
  (setq cbt_var_tset $value)
  (cbt_upd_imgset)
)

;atualiza o slide da hachura selecionada na lista
(defun cbt_upd_imgset ()
  (setq x (dimx_tile "cbt_img_set")
	y (dimy_tile "cbt_img_set"))
  (start_image "cbt_img_set")
  (fill_image  0 0 x y -2)
  (slide_image 0 -6 x y (strcat cnp_root "/slides/cbt_set_" cbt_var_tset ".sld"))
  (end_image)
)

;avalia se desenha a seta
(defun cbt_settog_action ()
  (setq cbt_var_dset $value)
  (cbt_eval_seta)
)

;controle de visibilidade
(defun cbt_eval_seta ()
  (if (= cbt_var_dset "1")
    (progn
      (mode_tile "cbt_lst_set" 0)
      (mode_tile "cbt_img_set" 0)
    )
    (progn
      (mode_tile "cbt_lst_set" 1)
      (mode_tile "cbt_img_set" 1)
    )
  )
)

;*********************************
;Hachuras                         
;*********************************

;ao selecionar uma hachura na lista
(defun cbt_lst_hchaction ()
  (setq cbt_var_thch $value)
  (cbt_upd_imghch)
)

;atualiza o slide da hachura selecionada na lista
(defun cbt_upd_imghch ()
  (setq x (dimx_tile "cbt_img_hch")
	y (dimy_tile "cbt_img_hch"))
  (start_image "cbt_img_hch")
  (fill_image  0 0 x y -2)
  (slide_image 0 -5 x y (strcat cnp_root "/slides/cbt_hch_" cbt_var_thch ".sld"))
  (end_image)
)
  
;avalia se é para hachurar
(defun cbt_hchtog_action ()
  (setq cbt_var_dhch $value)
  (cbt_eval_hatch)
)

;controle de visibilidade
(defun cbt_eval_hatch ()
  (if (= cbt_var_dhch "1")
    (progn
      (mode_tile "cbt_lst_hch" 0)
      (mode_tile "cbt_img_hch" 0)
    )
    (progn
      (mode_tile "cbt_lst_hch" 1)
      (mode_tile "cbt_img_hch" 1)
    )
  )
)

;*****************************************
;Atualização e Atuação dos Slides         
;*****************************************

(defun cbt_update_slides ()
  ;atualiza as imagens
  (setq x (dimx_tile "icon11")
	y (dimy_tile "icon11"))
  (start_image "icon11")
  (slide_image 0 0 x y (strcat cnp_root "/slides/cbt_11.sld"))
  (end_image)
  (setq x (dimx_tile "icon12")
	y (dimy_tile "icon12"))
  (start_image "icon12")
  (slide_image 0 0 x y (strcat cnp_root "/slides/cbt_12.sld"))
  (end_image)
  (setq x (dimx_tile "icon13")
	y (dimy_tile "icon13"))
  (start_image "icon13")
  (slide_image 0 0 x y (strcat cnp_root "/slides/cbt_13.sld"))
  (end_image)
  (setq x (dimx_tile "icon21")
	y (dimy_tile "icon21"))
  (start_image "icon21")
  (slide_image 0 0 x y (strcat cnp_root "/slides/cbt_21.sld"))
  (end_image)
  (setq x (dimx_tile "icon22")
	y (dimy_tile "icon22"))
  (start_image "icon22")
  (slide_image 0 0 x y (strcat cnp_root "/slides/cbt_22.sld"))
  (end_image)
  (setq x (dimx_tile "icon23")
	y (dimy_tile "icon23"))
  (start_image "icon23")
  (slide_image 0 0 x y (strcat cnp_root "/slides/cbt_23.sld"))
  (end_image)
  ;ações dos botões
  (action_tile "icon11" "(cbt_deftype)")
  (action_tile "icon12" "(cbt_deftype)")
  (action_tile "icon13" "(cbt_deftype)")
  (action_tile "icon21" "(cbt_deftype)")
  (action_tile "icon22" "(cbt_deftype)")
  (action_tile "icon23" "(cbt_deftype)")
)

;ação ao escolher o typo de cobertura
(defun cbt_deftype ()
  ;determina o tipo
  (setq cbt_var_type $key
	cbt_var_tipo (substr cbt_var_type 5 2)
  )
  ;atualiza o texto
  (cond
    ((= cbt_var_tipo "11") (set_tile "cbt_text_type" "Tipo Atual: Uma Água"))
    ((= cbt_var_tipo "12") (set_tile "cbt_text_type" "Tipo Atual: Duas Águas"))
    ((= cbt_var_tipo "13") (set_tile "cbt_text_type" "Tipo Atual: Três Águas"))
    ((= cbt_var_tipo "21") (set_tile "cbt_text_type" "Tipo Atual: Quatro Águas"))
    ((= cbt_var_tipo "22") (set_tile "cbt_text_type" "Tipo Atual: Seis Águas e 'L'"))
    ((= cbt_var_tipo "23") (set_tile "cbt_text_type" "Tipo Atual: Sete Águas em 'T'"))
  )
  ;lê os parâmetros do tipo de porta
)

;*****************************************
;Arquivo de Configurações                 
;*****************************************
  
;lê os dados iniciais da DCL no arquivo de dados
(defun cbt_last_file ()
  (if (findfile (strcat cnp_root "/config/cbt_last.txt"))
    (cbt_last_readfile)
    (progn
      (setq file (open (strcat cnp_root "/config/cbt_last.txt") "w" "utf8"))
      (write-line "11" file)
      (write-line "1" file)
      (write-line "0" file)
      (write-line "1.0" file)
      (write-line "1" file)
      (write-line "0" file)
      (write-line "1.0" file)
      (close file)
      (cbt_last_readfile)
    )
  )
)

;função que lê o arquivo de dados
(defun cbt_last_readfile ()
  (setq	file (open (strcat cnp_root "/config/cbt_last.txt") "r" "utf8"))
  (setq	cbt_var_tipo (read-line file))
  (setq	cbt_var_dhch (read-line file))
  (setq	cbt_var_thch (read-line file))
  (setq	cbt_var_fhch (read-line file))
  (setq	cbt_var_dset (read-line file))
  (setq	cbt_var_tset (read-line file))
  (setq	cbt_var_fset (read-line file))
  (close file)
)

;função que escreve o arquivo de dados
(defun cbt_last_writefile ()
  (setq	file (open (strcat cnp_root "/config/cbt_last.txt") "w" "utf8"))
  (write-line cbt_var_tipo file)
  (write-line cbt_var_dhch file)
  (write-line cbt_var_thch file)
  (write-line cbt_var_fhch file)
  (write-line cbt_var_dset file)
  (write-line cbt_var_tset file)
  (write-line cbt_var_fset file)
  (close file)
)


;********************************
;Cobertura Tipo - Coleta de Dados
;********************************
(defun c:cob () (cbt_getdata))

(defun cbt_getdata ()
  (cbt_draw_file)
  ;abre a caixa de diálogo
  (setq dcl_id (load_dialog (strcat cnp_root "/lisp/cadnorma.dcl")))
  (if (not (new_dialog "cbt_draw" dcl_id)) (exit))
  ;atualiza o slide
  (setq x (dimx_tile "cbt_draw_img")
	y (dimy_tile "cbt_draw_img"))
  (start_image "cbt_draw_img")
  (cond
    ((= cbt_var_tipo "11") (slide_image 0 0 x y (strcat cnp_root "/slides/cbt_draw_11.sld")))
    ((= cbt_var_tipo "12") (slide_image 0 0 x y (strcat cnp_root "/slides/cbt_draw_12.sld")))
    ((= cbt_var_tipo "13") (slide_image 0 0 x y (strcat cnp_root "/slides/cbt_draw_13.sld")))
    ((= cbt_var_tipo "21") (slide_image 0 0 x y (strcat cnp_root "/slides/cbt_draw_21.sld")))
    ((= cbt_var_tipo "22") (slide_image 0 0 x y (strcat cnp_root "/slides/cbt_draw_22.sld")))
    ((= cbt_var_tipo "23") (slide_image 0 0 x y (strcat cnp_root "/slides/cbt_draw_23.sld")))
  )
  (end_image)
  ;beiral
  (set_tile "cbt_draw_getp" cbt_drw_p)
  (action_tile "cbt_draw_getp" "(cbt_draw_evalget_p)")
  (action_tile "cbt_draw_pikp" "(done_dialog 8)")
  ;atualiza as medidas
  (set_tile "cbt_draw_geta" cbt_drw_a)
  (set_tile "cbt_draw_getb" cbt_drw_b)
  (set_tile "cbt_draw_getc" cbt_drw_c)
  (set_tile "cbt_draw_getd" cbt_drw_d)
  (set_tile "cbt_draw_gete" cbt_drw_e)
  (set_tile "cbt_draw_getf" cbt_drw_f)
  ;edit_boxes
  (action_tile "cbt_draw_geta" "(cbt_draw_evalget_a)")
  (action_tile "cbt_draw_getb" "(cbt_draw_evalget_b)")
  (action_tile "cbt_draw_getc" "(cbt_draw_evalget_c)")
  (action_tile "cbt_draw_getd" "(cbt_draw_evalget_d)")
  (action_tile "cbt_draw_gete" "(cbt_draw_evalget_e)")
  (action_tile "cbt_draw_getf" "(cbt_draw_evalget_f)")
  ;pick buttons
  (action_tile "cbt_draw_pika" "(done_dialog 2)")
  (action_tile "cbt_draw_pikb" "(done_dialog 3)")
  (action_tile "cbt_draw_pikc" "(done_dialog 4)")
  (action_tile "cbt_draw_pikd" "(done_dialog 5)")
  (action_tile "cbt_draw_pike" "(done_dialog 6)")
  (action_tile "cbt_draw_pikf" "(done_dialog 7)")
  ;mode_tile nas medidas
  (cond
    ((or (= cbt_var_tipo "11") (= cbt_var_tipo "12")
	 (= cbt_var_tipo "13") (= cbt_var_tipo "21")
     )
     (mode_tile "cbt_draw_geta" 0)
     (mode_tile "cbt_draw_getb" 0)
     (mode_tile "cbt_draw_getc" 1)
     (mode_tile "cbt_draw_getd" 1)
     (mode_tile "cbt_draw_gete" 1)
     (mode_tile "cbt_draw_getf" 1)
     (mode_tile "cbt_draw_pika" 0)
     (mode_tile "cbt_draw_pikb" 0)
     (mode_tile "cbt_draw_pikc" 1)
     (mode_tile "cbt_draw_pikd" 1)
     (mode_tile "cbt_draw_pike" 1)
     (mode_tile "cbt_draw_pikf" 1)
    )
    ((= cbt_var_tipo "22")
     (mode_tile "cbt_draw_geta" 0)
     (mode_tile "cbt_draw_getb" 0)
     (mode_tile "cbt_draw_getc" 0)
     (mode_tile "cbt_draw_getd" 0)
     (mode_tile "cbt_draw_gete" 1)
     (mode_tile "cbt_draw_getf" 1)
     (mode_tile "cbt_draw_pika" 0)
     (mode_tile "cbt_draw_pikb" 0)
     (mode_tile "cbt_draw_pikc" 0)
     (mode_tile "cbt_draw_pikd" 0)
     (mode_tile "cbt_draw_pike" 1)
     (mode_tile "cbt_draw_pikf" 1)
    )
    ((= cbt_var_tipo "23")
     (mode_tile "cbt_draw_geta" 0)
     (mode_tile "cbt_draw_getb" 0)
     (mode_tile "cbt_draw_getc" 0)
     (mode_tile "cbt_draw_getd" 0)
     (mode_tile "cbt_draw_gete" 0)
     (mode_tile "cbt_draw_getf" 1)
     (mode_tile "cbt_draw_pika" 0)
     (mode_tile "cbt_draw_pikb" 0)
     (mode_tile "cbt_draw_pikc" 0)
     (mode_tile "cbt_draw_pikd" 0)
     (mode_tile "cbt_draw_pike" 0)
     (mode_tile "cbt_draw_pikf" 1)
    )
  )
  ;funções ok_cancel
  (action_tile "cancel" "(done_dialog 0)")
  (action_tile "accept" "(done_dialog 1)")
  ;ativação da DCL
  (setq cbt_drw_dcl_id (start_dialog))
  (unload_dialog dcl_id)
  ;ações dos botões
  (if (= 1 cbt_drw_dcl_id) (cbt_draw_ok_action))
  (if (= 2 cbt_drw_dcl_id) (cbt_drw_pik_a))
  (if (= 3 cbt_drw_dcl_id) (cbt_drw_pik_b))
  (if (= 4 cbt_drw_dcl_id) (cbt_drw_pik_c))
  (if (= 5 cbt_drw_dcl_id) (cbt_drw_pik_d))
  (if (= 6 cbt_drw_dcl_id) (cbt_drw_pik_e))
  (if (= 7 cbt_drw_dcl_id) (cbt_drw_pik_f))
  (if (= 8 cbt_drw_dcl_id) (cbt_drw_pik_p))
  (princ)
)

(defun cbt_draw_ok_action ()
  (cbt_draw_writefile)
  (cond
    ((= cn7_dwgunit 1) (setq cbt_fator 0.01 cbt_blkscl 1.0))
    ((= cn7_dwgunit 100) (setq cbt_fator 1.0 cbt_blkscl 100.0))
    ((= cn7_dwgunit 1000) (setq cbt_fator 10.0 cbt_blkscl 1000.0))
  )
  (cond
    ((= cbt_var_tipo "11") (cbt_draw_01))
    ((= cbt_var_tipo "12") (cbt_draw_02))
    ((= cbt_var_tipo "13") (cbt_draw_03))
    ((= cbt_var_tipo "21") (cbt_draw_04))
    ((= cbt_var_tipo "22") (cbt_draw_05))
    ((= cbt_var_tipo "23") (cbt_draw_06))
  )
)

;comandos para os pick-points
(defun cbt_drw_pik_p ()
  (cbt_getdist_button)
  (if new_dist
    (progn
      (setq cbt_drw_p (rtos new_dist 2 2))
      (cbt_draw_writefile)
    )
  )
  (cbt_getdata)
)

(defun cbt_drw_pik_a ()
  (cbt_getdist_button)
  (if new_dist
    (progn
      (setq cbt_drw_a (rtos new_dist 2 2))
      (cbt_draw_writefile)
    )
  )
  (cbt_getdata)
)

(defun cbt_drw_pik_b ()
  (cbt_getdist_button)
  (if new_dist
    (progn
      (setq cbt_drw_b (rtos new_dist 2 2))
      (cbt_draw_writefile)
    )
  )
  (cbt_getdata)
)

(defun cbt_drw_pik_c ()
  (cbt_getdist_button)
  (if new_dist
    (progn
      (setq cbt_drw_c (rtos new_dist 2 2))
      (cbt_draw_writefile)
    )
  )
  (cbt_getdata)
)

(defun cbt_drw_pik_d ()
  (cbt_getdist_button)
  (if new_dist
    (progn
      (setq cbt_drw_d (rtos new_dist 2 2))
      (cbt_draw_writefile)
    )
  )
  (cbt_getdata)
)

(defun cbt_drw_pik_e ()
  (cbt_getdist_button)
  (if new_dist
    (progn
      (setq cbt_drw_e (rtos new_dist 2 2))
      (cbt_draw_writefile)
    )
  )
  (cbt_getdata)
)

(defun cbt_drw_pik_f ()
  (cbt_getdist_button)
  (if new_dist
    (progn
      (setq cbt_drw_f (rtos new_dist 2 2))
      (cbt_draw_writefile)
    )
  )
  (cbt_getdata)
)

;çlica em dois pontos para confirmar as medidas
(defun cbt_getdist_button ()
  (cbt_draw_writefile)
  (setq get_dist nil
	pt1 (getpoint "\nPrimeiro ponto para definir a medida...: ")
	pt2 (getpoint pt1 "Segundo ponto para definir a medida...: ")
	get_dist (distance pt1 pt2)
  )
  (cond
    ((= cn7_dwgunit 1.0) (setq new_dist (* get_dist 100.0)))
    ((= cn7_dwgunit 100.0) (setq new_dist (* get_dist 1.0)))
    ((= cn7_dwgunit 1000.0) (setq new_dist (* get_dist 0.1)))
  )
)

;verifica se o valor entrado é válido para as medidas
(defun cbt_draw_evalget_p ()
  (setq cbt_drw_new_p $value)
  (if (distof cbt_drw_new_p)
    (setq cbt_drw_p cbt_drw_new_p)
    (progn
      (alert "Valor Inválido!\nDigite um número Real.")
      (set_tile "cbt_draw_getp" cbt_drw_p)
      (mode_tile "cbt_draw_getp" 2)
    )
  )
)  

(defun cbt_draw_evalget_a ()
  (setq cbt_drw_new_a $value)
  (if (distof cbt_drw_new_a)
    (setq cbt_drw_a cbt_drw_new_a)
    (progn
      (alert "Valor Inválido!\nDigite um número Real.")
      (set_tile "cbt_draw_geta" cbt_drw_a)
      (mode_tile "cbt_draw_geta" 2)
    )
  )
)  

(defun cbt_draw_evalget_b ()
  (setq cbt_drw_new_b $value)
  (if (distof cbt_drw_new_b)
    (setq cbt_drw_b cbt_drw_new_b)
    (progn
      (alert "Valor Inválido!\nDigite um número Real.")
      (set_tile "cbt_draw_getb" cbt_drw_b)
      (mode_tile "cbt_draw_getb" 2)
    )
  )
)

(defun cbt_draw_evalget_c ()
  (setq cbt_drw_new_c $value)
  (if (distof cbt_drw_new_c)
    (setq cbt_drw_c cbt_drw_new_c)
    (progn
      (alert "Valor Inválido!\nDigite um número Real.")
      (set_tile "cbt_draw_getc" cbt_drw_c)
      (mode_tile "cbt_draw_getc" 2)
    )
  )
)

(defun cbt_draw_evalget_d ()
  (setq cbt_drw_new_d $value)
  (if (distof cbt_drw_new_d)
    (setq cbt_drw_d cbt_drw_new_d)
    (progn
      (alert "Valor Inválido!\nDigite um número Real.")
      (set_tile "cbt_draw_getd" cbt_drw_d)
      (mode_tile "cbt_draw_getd" 2)
    )
  )
)

(defun cbt_draw_evalget_e ()
  (setq cbt_drw_new_e $value)
  (if (distof cbt_drw_new_e)
    (setq cbt_drw_e cbt_drw_new_e)
    (progn
      (alert "Valor Inválido!\nDigite um número Real.")
      (set_tile "cbt_draw_gete" cbt_drw_e)
      (mode_tile "cbt_draw_gete" 2)
    )
  )
)

(defun cbt_draw_evalget_f ()
  (setq cbt_drw_new_f $value)
  (if (distof cbt_drw_new_f)
    (setq cbt_drw_f cbt_drw_new_f)
    (progn
      (alert "Valor Inválido!\nDigite um número Real.")
      (set_tile "cbt_draw_getf" cbt_drw_f)
      (mode_tile "cbt_draw_getf" 2)
    )
  )
)


;*****************************************
;Arquivo de Configurações                 
;*****************************************
  
;lê os dados iniciais da DCL no arquivo de dados
(defun cbt_draw_file ()
  (if (findfile (strcat cnp_root "/config/cbt_draw.txt"))
    (cbt_draw_readfile)
    (progn
      (setq file (open (strcat cnp_root "/config/cbt_draw.txt") "w" "utf8"))
      (write-line "100" file)
      (write-line "600" file)
      (write-line "200" file)
      (write-line "600" file)
      (write-line "200" file)
      (write-line "200" file)
      (write-line "200" file)
      (close file)
      (cbt_draw_readfile)
    )
  )
)

;função que lê o arquivo de dados
(defun cbt_draw_readfile ()
  (setq	file (open (strcat cnp_root "/config/cbt_draw.txt") "r" "utf8"))
  (setq	cbt_drw_p (read-line file))
  (setq	cbt_drw_a (read-line file))
  (setq	cbt_drw_b (read-line file))
  (setq	cbt_drw_c (read-line file))
  (setq	cbt_drw_d (read-line file))
  (setq	cbt_drw_e (read-line file))
  (setq	cbt_drw_f (read-line file))
  (close file)
)

;função que escreve o arquivo de dados
(defun cbt_draw_writefile ()
  (setq	file (open (strcat cnp_root "/config/cbt_draw.txt") "w" "utf8"))
  (write-line cbt_drw_p file)
  (write-line cbt_drw_a file)
  (write-line cbt_drw_b file)
  (write-line cbt_drw_c file)
  (write-line cbt_drw_d file)
  (write-line cbt_drw_e file)
  (write-line cbt_drw_f file)
  (close file)
)



;*****************************************
;Desenho das coberturas                   
;*****************************************


;desenho da cobertura tipo 01
;duas águas simples
(defun c:cb1 () (cbt_draw_01))

(defun cbt_draw_01 ()
  (setq ss_hatch (ssadd))
  (guarda '("blipmode" "cecolor" "celtype" "clayer" "cmdecho" "orthomode"
          "textstyle" "luprec" "osmode" ))
  (cbt_layc_readfile)
  (setq cb1_pt0 (getpoint "\nClique no ponto base...")
	cb1_angbase (getangle cb1_pt0 "\nÂngulo para desenho...")
	cb1_pt1 (polar cb1_pt0 cb1_angbase (* cbt_fator (distof cbt_drw_a)))
	cb1_pt2 (polar cb1_pt1 (+ cb1_angbase (/ pi 2)) (* cbt_fator (distof cbt_drw_b)))
	cb1_pt3 (polar cb1_pt0 (+ cb1_angbase (/ pi 2)) (* cbt_fator (distof cbt_drw_b)))
	cb1_pt3a (polar cb1_pt0 (- cb1_angbase (/ pi 2)) (* cbt_fator (distof cbt_drw_p)))
	cb1_pt4 (polar cb1_pt3a (+ cb1_angbase pi) (* cbt_fator (distof cbt_drw_p)))
	cb1_pt5 (polar cb1_pt4 cb1_angbase (+ (* cbt_fator (distof cbt_drw_a)) (* 2.0 cbt_fator (distof cbt_drw_p))))
	cb1_pt6 (polar cb1_pt5 (+ cb1_angbase (/ pi 2))
		       (+ (* cbt_fator (distof cbt_drw_b)) (* 2.0 cbt_fator (distof cbt_drw_p))))
	cb1_pt7 (polar cb1_pt4 (+ cb1_angbase (/ pi 2))
		       (+ (* cbt_fator (distof cbt_drw_b)) (* 2.0 cbt_fator (distof cbt_drw_p))))
	cb1_pt0a (polar cb1_pt0 cb1_angbase (/ (distance cb1_pt0 cb1_pt1) 2.0))
	cb1_pt8 (polar cb1_pt0a (+ cb1_angbase (/ pi 2)) (* 0.5 cbt_fator (distof cbt_drw_b)))			
  )
  (setq grp_type "2")
  (cn7_find_blkscl)
  ;Desenha a Projeção da Edificação
  (cn7_verylayer cbt_layc_edl 7)
  (setvar "cecolor" cbt_layc_edc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" cb1_pt0 "_non" cb1_pt1 "_non" cb1_pt2 "_non" cb1_pt3 "_c")
  (cn7_verylayer cbt_layc_cbl 7)
  (setvar "cecolor" cbt_layc_cbc)
  (setvar "celtype" "bylayer")
  (command "._pline" "_non" cb1_pt4 "_non" cb1_pt5 "_non" cb1_pt6 "_non" cb1_pt7 "_c")
  (setq ss_hatch (ssadd (entlast) ss_hatch))
  ;insere a seta
  (if (= cbt_var_dset "1")
    (progn
      (setq cb1_setang (/ (* cb1_angbase 180) pi))
      (command "._insert" (strcat cnp_root "/blocos/cbt_seta_" cbt_var_tset ".dwg")
	       "_s" (* cbt_blkscl (distof cbt_var_fset)) "_non" cb1_pt8 cb1_setang)
      (setq ss_hatch (ssadd (entlast) ss_hatch))
    )
  )
  ;desenha a hachura
  (if (= cbt_var_dhch "1")
    (progn
      (cond
	((= cbt_var_thch "0")
	 (setvar "hpname" "ansi31")
	 (setq cb1_hch_maisang 45
	       cb1_hch_scale 0.25
	 )
	)
	((= cbt_var_thch "1")
	 (setvar "hpname" "telha1")
	 (setq cb1_hch_maisang 0
	       cb1_hch_scale 1.0
	 )
	)
	((= cbt_var_thch "2")
	 (setvar "hpname" "telha2")
	 (setq cb1_hch_maisang 0
	       cb1_hch_scale 1.0
	 )
	)
	((= cbt_var_thch "3")
	 (setvar "hpname" "telha3")
	 (setq cb1_hch_maisang 0
	       cb1_hch_scale 1.0
	 )
	)
	((= cbt_var_thch "4")
	 (setvar "hpname" "telha4")
	 (setq cb1_hch_maisang 0
	       cb1_hch_scale 1.0
	 )
	)
	((= cbt_var_thch "5")
	 (setvar "hpname" "telha5")
	 (setq cb1_hch_maisang 0
	       cb1_hch_scale 1.0
	 )
	)
	((= cbt_var_thch "6")
	 (setvar "hpname" "telha6")
	 (setq cb1_hch_maisang 0
	       cb1_hch_scale 1.0
	 )
	)
	((= cbt_var_thch "7")
	 (setvar "hpname" "telha7")
	 (setq cb1_hch_maisang 0
	       cb1_hch_scale 1.0
	 )
	)
      )
      (cn7_verylayer cbt_layc_hcl 7)
      (setvar "cecolor" cbt_layc_hcc)
      (setvar "celtype" "bylayer")
      (command "._bhatch" "_s" ss_hatch "" "_p" ""
	       (* (distof cbt_var_fhch) cn7_blkscl cb1_hch_scale) ;escala
	       (+ (+ cb1_hch_maisang (/ (* cb1_angbase 180.0) pi)) 90) ; ângulo
	       "_a" "_s" "_o" "" ""
      )
    )
  )
  (devolve)
  (princ)
)

;desenho da cobertura tipo 02
;duas águas simples
(defun c:cb2 () (cbt_draw_02))

(defun cbt_draw_02 ()
  (setq ss_hatch1 (ssadd)
	ss_hatch2 (ssadd)
  )
  (guarda '("blipmode" "cecolor" "celtype" "clayer" "cmdecho" "orthomode"
          "textstyle" "luprec" "osmode" ))
  (cbt_layc_readfile)
  (setq cb2_pt0 (getpoint "\nClique no ponto base...")
	cb2_angbase (getangle cb2_pt0 "\nÂngulo para desenho...")
	cb2_pt1 (polar cb2_pt0 cb2_angbase (* cbt_fator (distof cbt_drw_a)))
	cb2_pt2 (polar cb2_pt1 (+ cb2_angbase (/ pi 2)) (* cbt_fator (distof cbt_drw_b)))
	cb2_pt3 (polar cb2_pt0 (+ cb2_angbase (/ pi 2)) (* cbt_fator (distof cbt_drw_b)))
	cb2_pt3a (polar cb2_pt0 (- cb2_angbase (/ pi 2)) (* cbt_fator (distof cbt_drw_p)))
	cb2_pt4 (polar cb2_pt3a (+ cb2_angbase pi) (* cbt_fator (distof cbt_drw_p)))
	cb2_pt5 (polar cb2_pt4 cb2_angbase (+ (* cbt_fator (distof cbt_drw_a)) (* 2.0 cbt_fator (distof cbt_drw_p))))
	cb2_pt6 (polar cb2_pt5 (+ cb2_angbase (/ pi 2))
		       (+ (* cbt_fator (distof cbt_drw_b)) (* 2.0 cbt_fator (distof cbt_drw_p))))
	cb2_pt7 (polar cb2_pt4 (+ cb2_angbase (/ pi 2))
		       (+ (* cbt_fator (distof cbt_drw_b)) (* 2.0 cbt_fator (distof cbt_drw_p))))
	cb2_pt0a (polar cb2_pt0 cb2_angbase (/ (distance cb2_pt0 cb2_pt1) 2.0))
	cb2_pt8 (polar cb2_pt4 (+ cb2_angbase (/ pi 2)) (/ (distance cb2_pt4 cb2_pt7) 2))
	cb2_pt9 (polar cb2_pt5 (+ cb2_angbase (/ pi 2)) (/ (distance cb2_pt5 cb2_pt6) 2))
	cb2_pt8a (polar cb2_pt8 cb2_angbase (/ (distance cb2_pt8 cb2_pt9) 2))
	cb2_pt10 (polar cb2_pt8a (+ cb2_angbase (/ pi 2)) (/ (distance cb2_pt9 cb2_pt6) 2))
	cb2_pt11 (polar cb2_pt8a (- cb2_angbase (/ pi 2)) (/ (distance cb2_pt9 cb2_pt5) 2))
  )
  (setq grp_type "2")
  (cn7_find_blkscl)
  (command "._undo" "_m")
  ;Desenha a Projeção da Edificação
  (cn7_verylayer cbt_layc_edl 7)
  (setvar "cecolor" cbt_layc_edc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" cb2_pt0 "_non" cb2_pt1 "_non" cb2_pt2 "_non" cb2_pt3 "_c")
  ;desenha o contorno da cobertura
  (cn7_verylayer cbt_layc_cbl 7)
  (setvar "cecolor" cbt_layc_cbc)
  (setvar "celtype" "bylayer")
  (command "._line" "_non" cb2_pt4 "_non" cb2_pt5 "")
  (setq ss_hatch1 (ssadd (entlast) ss_hatch1))
  (command "._line" "_non" cb2_pt5 "_non" cb2_pt9 "")
  (setq ss_hatch1 (ssadd (entlast) ss_hatch1))
  (command "._line" "_non" cb2_pt8 "_non" cb2_pt9 "")
  (setq ss_hatch1 (ssadd (entlast) ss_hatch1))
  (setq ss_hatch2 (ssadd (entlast) ss_hatch2))
  (command "._line" "_non" cb2_pt8 "_non" cb2_pt4 "")
  (setq ss_hatch1 (ssadd (entlast) ss_hatch1))
  (command "._line" "_non" cb2_pt8 "_non" cb2_pt7 "")
  (setq ss_hatch2 (ssadd (entlast) ss_hatch2))
  (command "._line" "_non" cb2_pt6 "_non" cb2_pt7 "")
  (setq ss_hatch2 (ssadd (entlast) ss_hatch2))
  (command "._line" "_non" cb2_pt9 "_non" cb2_pt6 "")
  (setq ss_hatch2 (ssadd (entlast) ss_hatch2))

  ;insere a seta
  (if (= cbt_var_dset "1")
    (progn
      (setq cb2_setang (/ (* cb2_angbase 180) pi))
      (command "._insert" (strcat cnp_root "/blocos/cbt_seta_" cbt_var_tset ".dwg")
	       "_s" (* cbt_blkscl (distof cbt_var_fset)) "_non" cb2_pt10 (+ cb2_setang 90))
      (setq ss_hatch2 (ssadd (entlast) ss_hatch2))
      (command "._insert" (strcat cnp_root "/blocos/cbt_seta_" cbt_var_tset ".dwg")
	       "_s" (* cbt_blkscl (distof cbt_var_fset)) "_non" cb2_pt11 (- cb2_setang 90))
      (setq ss_hatch1 (ssadd (entlast) ss_hatch1))
    )
  )
  ;desenha a hachura
  (if (= cbt_var_dhch "1")
    (progn
      (cond
	((= cbt_var_thch "0")
	 (setvar "hpname" "ansi31")
	 (setq cb2_hch_maisang 45
	       cb2_hch_scale 0.25
	 )
	)
	((= cbt_var_thch "1")
	 (setvar "hpname" "telha1")
	 (setq cb2_hch_maisang 0
	       cb2_hch_scale 1.0
	 )
	)
	((= cbt_var_thch "2")
	 (setvar "hpname" "telha2")
	 (setq cb2_hch_maisang 0
	       cb2_hch_scale 1.0
	 )
	)
	((= cbt_var_thch "3")
	 (setvar "hpname" "telha3")
	 (setq cb2_hch_maisang 0
	       cb2_hch_scale 1.0
	 )
	)
	((= cbt_var_thch "4")
	 (setvar "hpname" "telha4")
	 (setq cb2_hch_maisang 0
	       cb2_hch_scale 1.0
	 )
	)
	((= cbt_var_thch "5")
	 (setvar "hpname" "telha5")
	 (setq cb2_hch_maisang 0
	       cb2_hch_scale 1.0
	 )
	)
	((= cbt_var_thch "6")
	 (setvar "hpname" "telha6")
	 (setq cb2_hch_maisang 0
	       cb2_hch_scale 1.0
	 )
	)
	((= cbt_var_thch "7")
	 (setvar "hpname" "telha7")
	 (setq cb2_hch_maisang 0
	       cb2_hch_scale 1.0
	 )
	)
      )
      (cn7_verylayer cbt_layc_hcl 7)
      (setvar "cecolor" cbt_layc_hcc)
      (setvar "celtype" "bylayer")
      (command "._bhatch" "_s" ss_hatch1 "" "_p" ""
	       (* (distof cbt_var_fhch) cn7_blkscl cb2_hch_scale) ;escala
	       (+ cb2_hch_maisang (/ (* cb2_angbase 180.0) pi)) ; ângulo
	       "_a" "_s" "_o" "" ""
      )
      (command "._bhatch" "_s" ss_hatch2 "" "_p" ""
	       (* (distof cbt_var_fhch) cn7_blkscl cb2_hch_scale) ;escala
	       (+ (+ cb2_hch_maisang (/ (* cb2_angbase 180.0) pi)) 180) ; ângulo
	       "_a" "_s" "_o" "" ""
      )
    )
  )
  (devolve)
  (prompt "\nUse o comando <UB> para retornar... ")
  (princ)
)

;desenho da cobertura tipo 03
;duas águas simples
(defun c:cb3 () (cbt_draw_03))

(defun cbt_draw_03 ()
  (setq ss_hatch1 (ssadd)
	ss_hatch2 (ssadd)
	ss_hatch3 (ssadd)
  )
  (guarda '("blipmode" "cecolor" "celtype" "clayer" "cmdecho" "orthomode"
          "textstyle" "luprec" "osmode" ))
  (cbt_layc_readfile)
  (setq cb3_pt0 (getpoint "\nClique no ponto base...")
	cb3_angbase (getangle cb3_pt0 "\nÂngulo para desenho...")
	cb3_pt1 (polar cb3_pt0 cb3_angbase (* cbt_fator (distof cbt_drw_a)))
	cb3_pt2 (polar cb3_pt1 (+ cb3_angbase (/ pi 2)) (* cbt_fator (distof cbt_drw_b)))
	cb3_pt3 (polar cb3_pt0 (+ cb3_angbase (/ pi 2)) (* cbt_fator (distof cbt_drw_b)))
	cb3_pt3a (polar cb3_pt0 (- cb3_angbase (/ pi 2)) (* cbt_fator (distof cbt_drw_p)))
	cb3_pt4 (polar cb3_pt3a (+ cb3_angbase pi) (* cbt_fator (distof cbt_drw_p)))
	cb3_pt5 (polar cb3_pt4 cb3_angbase (+ (* cbt_fator (distof cbt_drw_a)) (* 2.0 cbt_fator (distof cbt_drw_p))))
	cb3_pt6 (polar cb3_pt5 (+ cb3_angbase (/ pi 2))
		       (+ (* cbt_fator (distof cbt_drw_b)) (* 2.0 cbt_fator (distof cbt_drw_p))))
	cb3_pt7 (polar cb3_pt4 (+ cb3_angbase (/ pi 2))
		       (+ (* cbt_fator (distof cbt_drw_b)) (* 2.0 cbt_fator (distof cbt_drw_p))))
	cb3_pt0a (polar cb3_pt0 cb3_angbase (/ (distance cb3_pt0 cb3_pt1) 2.0))
	cb3_pt8 (polar cb3_pt4 (+ cb3_angbase (/ pi 2)) (/ (distance cb3_pt4 cb3_pt7) 2))
	cb3_pt9 (polar cb3_pt8 cb3_angbase (- (distance cb3_pt7 cb3_pt6) (distance cb3_pt7 cb3_pt8)))
	cb3_pt8a (polar cb3_pt8 cb3_angbase (/ (distance cb3_pt8 cb3_pt9) 2))
	cb3_pt10 (polar cb3_pt8a (- cb3_angbase (/ pi 2)) (/ (distance cb3_pt4 cb3_pt8) 2))
	cb3_pt11 (polar cb3_pt8a (+ cb3_angbase (/ pi 2)) (/ (distance cb3_pt4 cb3_pt8) 2))
	cb3_pt12 (polar cb3_pt9 cb3_angbase (/ (distance cb3_pt4 cb3_pt8) 2))
  )
  (setq grp_type "2")
  (cn7_find_blkscl)
  (command "._undo" "_m")
  ;Desenha a Projeção da Edificação
  (cn7_verylayer cbt_layc_edl 7)
  (setvar "cecolor" cbt_layc_edc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" cb3_pt0 "_non" cb3_pt1 "_non" cb3_pt2 "_non" cb3_pt3 "_c")
  ;desenha o contorno da cobertura
  (cn7_verylayer cbt_layc_cbl 7)
  (setvar "cecolor" cbt_layc_cbc)
  (setvar "celtype" "bylayer")
  (command "._line" "_non" cb3_pt4 "_non" cb3_pt5 "")
  (setq ss_hatch1 (ssadd (entlast) ss_hatch1))
  (command "._line" "_non" cb3_pt5 "_non" cb3_pt9 "")
  (setq ss_hatch1 (ssadd (entlast) ss_hatch1))
  (setq ss_hatch3 (ssadd (entlast) ss_hatch3))
  (command "._line" "_non" cb3_pt8 "_non" cb3_pt9 "")
  (setq ss_hatch1 (ssadd (entlast) ss_hatch1))
  (setq ss_hatch2 (ssadd (entlast) ss_hatch2))
  (command "._line" "_non" cb3_pt8 "_non" cb3_pt4 "")
  (setq ss_hatch1 (ssadd (entlast) ss_hatch1))
  (command "._line" "_non" cb3_pt8 "_non" cb3_pt7 "")
  (setq ss_hatch2 (ssadd (entlast) ss_hatch2))
  (command "._line" "_non" cb3_pt6 "_non" cb3_pt7 "")
  (setq ss_hatch2 (ssadd (entlast) ss_hatch2))
  (command "._line" "_non" cb3_pt9 "_non" cb3_pt6 "")
  (setq ss_hatch2 (ssadd (entlast) ss_hatch2))
  (setq ss_hatch3 (ssadd (entlast) ss_hatch3))
  (command "._line" "_non" cb3_pt5 "_non" cb3_pt6 "")
  (setq ss_hatch3 (ssadd (entlast) ss_hatch3))
  ;insere a seta
  (if (= cbt_var_dset "1")
    (progn
      (setq cb3_setang (/ (* cb3_angbase 180) pi))
      (command "._insert" (strcat cnp_root "/blocos/cbt_seta_" cbt_var_tset ".dwg")
	       "_s" (* cbt_blkscl (distof cbt_var_fset)) "_non" cb3_pt10 (- cb3_setang 90))
      (setq ss_hatch1 (ssadd (entlast) ss_hatch1))
      (command "._insert" (strcat cnp_root "/blocos/cbt_seta_" cbt_var_tset ".dwg")
	       "_s" (* cbt_blkscl (distof cbt_var_fset)) "_non" cb3_pt11 (+ cb3_setang 90))
      (setq ss_hatch2 (ssadd (entlast) ss_hatch2))
      (command "._insert" (strcat cnp_root "/blocos/cbt_seta_" cbt_var_tset ".dwg")
	       "_s" (* cbt_blkscl (distof cbt_var_fset)) "_non" cb3_pt12 cb3_setang)
      (setq ss_hatch3 (ssadd (entlast) ss_hatch3))
    )
  )
  ;desenha a hachura
  (if (= cbt_var_dhch "1")
    (progn
      (cond
	((= cbt_var_thch "0")
	 (setvar "hpname" "ansi31")
	 (setq cb3_hch_maisang 45
	       cb3_hch_scale 0.25
	 )
	)
	((= cbt_var_thch "1")
	 (setvar "hpname" "telha1")
	 (setq cb3_hch_maisang 0
	       cb3_hch_scale 1.0
	 )
	)
	((= cbt_var_thch "2")
	 (setvar "hpname" "telha2")
	 (setq cb3_hch_maisang 0
	       cb3_hch_scale 1.0
	 )
	)
	((= cbt_var_thch "3")
	 (setvar "hpname" "telha3")
	 (setq cb3_hch_maisang 0
	       cb3_hch_scale 1.0
	 )
	)
	((= cbt_var_thch "4")
	 (setvar "hpname" "telha4")
	 (setq cb3_hch_maisang 0
	       cb3_hch_scale 1.0
	 )
	)
	((= cbt_var_thch "5")
	 (setvar "hpname" "telha5")
	 (setq cb3_hch_maisang 0
	       cb3_hch_scale 1.0
	 )
	)
	((= cbt_var_thch "6")
	 (setvar "hpname" "telha6")
	 (setq cb3_hch_maisang 0
	       cb3_hch_scale 1.0
	 )
	)
	((= cbt_var_thch "7")
	 (setvar "hpname" "telha7")
	 (setq cb3_hch_maisang 0
	       cb3_hch_scale 1.0
	 )
	)
      )
      (cn7_verylayer cbt_layc_hcl 7)
      (setvar "cecolor" cbt_layc_hcc)
      (setvar "celtype" "bylayer")
      (command "._bhatch" "_s" ss_hatch1 "" "_p" ""
	       (* (distof cbt_var_fhch) cn7_blkscl cb3_hch_scale) ;escala
	       (+ cb3_hch_maisang (/ (* cb3_angbase 180.0) pi)) ; ângulo
	       "_a" "_s" "_o" "" ""
      )
      (command "._bhatch" "_s" ss_hatch2 "" "_p" ""
	       (* (distof cbt_var_fhch) cn7_blkscl cb3_hch_scale) ;escala
	       (+ (+ cb3_hch_maisang (/ (* cb3_angbase 180.0) pi)) 180) ; ângulo
	       "_a" "_s" "_o" "" ""
      )
      (command "._bhatch" "_s" ss_hatch3 "" "_p" ""
	       (* (distof cbt_var_fhch) cn7_blkscl cb3_hch_scale) ;escala
	       (+ (+ cb3_hch_maisang (/ (* cb3_angbase 180.0) pi)) 90) ; ângulo
	       "_a" "_s" "_o" "" ""
      )
    )
  )
  (devolve)
  (prompt "\nUse o comando <UB> para retornar... ")
  (princ)
)

;desenho da cobertura tipo 04
;duas águas simples
(defun c:cb4 () (cbt_draw_04))

(defun cbt_draw_04 ()
  (setq ss_hatch1 (ssadd)
	ss_hatch2 (ssadd)
	ss_hatch3 (ssadd)
	ss_hatch4 (ssadd)
  )
  (guarda '("blipmode" "cecolor" "celtype" "clayer" "cmdecho" "orthomode"
          "textstyle" "luprec" "osmode" ))
  (cbt_layc_readfile)
  (setq cb4_pt0 (getpoint "\nClique no ponto base...")
	cb4_angbase (getangle cb4_pt0 "\nÂngulo para desenho...")
	cb4_pt1 (polar cb4_pt0 cb4_angbase (* cbt_fator (distof cbt_drw_a)))
	cb4_pt2 (polar cb4_pt1 (+ cb4_angbase (/ pi 2)) (* cbt_fator (distof cbt_drw_b)))
	cb4_pt3 (polar cb4_pt0 (+ cb4_angbase (/ pi 2)) (* cbt_fator (distof cbt_drw_b)))
	cb4_pt3a (polar cb4_pt0 (- cb4_angbase (/ pi 2)) (* cbt_fator (distof cbt_drw_p)))
	cb4_pt4 (polar cb4_pt3a (+ cb4_angbase pi) (* cbt_fator (distof cbt_drw_p)))
	cb4_pt5 (polar cb4_pt4 cb4_angbase (+ (* cbt_fator (distof cbt_drw_a)) (* 2.0 cbt_fator (distof cbt_drw_p))))
	cb4_pt6 (polar cb4_pt5 (+ cb4_angbase (/ pi 2))
		       (+ (* cbt_fator (distof cbt_drw_b)) (* 2.0 cbt_fator (distof cbt_drw_p))))
	cb4_pt7 (polar cb4_pt4 (+ cb4_angbase (/ pi 2))
		       (+ (* cbt_fator (distof cbt_drw_b)) (* 2.0 cbt_fator (distof cbt_drw_p))))
	cb4_pt4a (polar cb4_pt4 (+ cb4_angbase (/ pi 2)) (/ (distance cb4_pt4 cb4_pt7) 2))
	cb4_pt8 (polar cb4_pt4a cb4_angbase (/ (distance cb4_pt4 cb4_pt7) 2))
	cb4_pt5a (polar cb4_pt5 (+ cb4_angbase (/ pi 2)) (/ (distance cb4_pt4 cb4_pt7) 2))
	cb4_pt9 (polar cb4_pt5a (+ pi cb4_angbase) (/ (distance cb4_pt4 cb4_pt7) 2))
	cb4_pt8a (polar cb4_pt8 cb4_angbase (/ (distance cb4_pt8 cb4_pt9) 2))
	cb4_pt10 (polar cb4_pt8a (- cb4_angbase (/ pi 2)) (/ (distance cb4_pt5 cb4_pt6) 4))
	cb4_pt11 (polar cb4_pt8a (+ cb4_angbase (/ pi 2)) (/ (distance cb4_pt5 cb4_pt6) 4))
	cb4_pt12 (polar cb4_pt9 cb4_angbase (/ (distance cb4_pt5 cb4_pt6) 4))
	cb4_pt13 (polar cb4_pt8 (+ pi cb4_angbase) (/ (distance cb4_pt5 cb4_pt6) 4))
  )
  (setq grp_type "2")
  (cn7_find_blkscl)
  (command "._undo" "_m")
  ;Desenha a Projeção da Edificação
  (cn7_verylayer cbt_layc_edl 7)
  (setvar "cecolor" cbt_layc_edc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" cb4_pt0 "_non" cb4_pt1 "_non" cb4_pt2 "_non" cb4_pt3 "_c")
  ;desenha o contorno da cobertura
  (cn7_verylayer cbt_layc_cbl 7)
  (setvar "cecolor" cbt_layc_cbc)
  (setvar "celtype" "bylayer")
  (command "._line" "_non" cb4_pt4 "_non" cb4_pt5 "")
  (setq ss_hatch1 (ssadd (entlast) ss_hatch1))
  (command "._line" "_non" cb4_pt5 "_non" cb4_pt9 "")
  (setq ss_hatch1 (ssadd (entlast) ss_hatch1))
  (setq ss_hatch3 (ssadd (entlast) ss_hatch3))  
  (command "._line" "_non" cb4_pt8 "_non" cb4_pt9 "")
  (setq ss_hatch1 (ssadd (entlast) ss_hatch1))
  (setq ss_hatch2 (ssadd (entlast) ss_hatch2))
  (command "._line" "_non" cb4_pt8 "_non" cb4_pt4 "")
  (setq ss_hatch1 (ssadd (entlast) ss_hatch1))
  (setq ss_hatch4 (ssadd (entlast) ss_hatch4))
  (command "._line" "_non" cb4_pt8 "_non" cb4_pt7 "")
  (setq ss_hatch2 (ssadd (entlast) ss_hatch2))
  (setq ss_hatch4 (ssadd (entlast) ss_hatch4))
  (command "._line" "_non" cb4_pt6 "_non" cb4_pt7 "")
  (setq ss_hatch2 (ssadd (entlast) ss_hatch2))
  (command "._line" "_non" cb4_pt9 "_non" cb4_pt6 "")
  (setq ss_hatch2 (ssadd (entlast) ss_hatch2))
  (setq ss_hatch3 (ssadd (entlast) ss_hatch3))
  (command "._line" "_non" cb4_pt5 "_non" cb4_pt6 "")
  (setq ss_hatch3 (ssadd (entlast) ss_hatch3))
  (command "._line" "_non" cb4_pt4 "_non" cb4_pt7 "")
  (setq ss_hatch4 (ssadd (entlast) ss_hatch4))
  ;insere a seta
  (if (= cbt_var_dset "1")
    (progn
      (setq cb4_setang (/ (* cb4_angbase 180) pi))
      (command "._insert" (strcat cnp_root "/blocos/cbt_seta_" cbt_var_tset ".dwg")
	       "_s" (* cbt_blkscl (distof cbt_var_fset)) "_non" cb4_pt10 (- cb4_setang 90))
      (setq ss_hatch1 (ssadd (entlast) ss_hatch1))
      (command "._insert" (strcat cnp_root "/blocos/cbt_seta_" cbt_var_tset ".dwg")
	       "_s" (* cbt_blkscl (distof cbt_var_fset)) "_non" cb4_pt11 (+ cb4_setang 90))
      (setq ss_hatch2 (ssadd (entlast) ss_hatch2))
      (command "._insert" (strcat cnp_root "/blocos/cbt_seta_" cbt_var_tset ".dwg")
	       "_s" (* cbt_blkscl (distof cbt_var_fset)) "_non" cb4_pt12 cb4_setang)
      (setq ss_hatch3 (ssadd (entlast) ss_hatch3))
      (command "._insert" (strcat cnp_root "/blocos/cbt_seta_" cbt_var_tset ".dwg")
	       "_s" (* cbt_blkscl (distof cbt_var_fset)) "_non" cb4_pt13 (+ 180 cb4_setang))
      (setq ss_hatch4 (ssadd (entlast) ss_hatch4))
    )
  )
  ;desenha a hachura
  (if (= cbt_var_dhch "1")
    (progn
      (cond
	((= cbt_var_thch "0")
	 (setvar "hpname" "ansi31")
	 (setq cb4_hch_maisang 45
	       cb4_hch_scale 0.25
	 )
	)
	((= cbt_var_thch "1")
	 (setvar "hpname" "telha1")
	 (setq cb4_hch_maisang 0
	       cb4_hch_scale 1.0
	 )
	)
	((= cbt_var_thch "2")
	 (setvar "hpname" "telha2")
	 (setq cb4_hch_maisang 0
	       cb4_hch_scale 1.0
	 )
	)
	((= cbt_var_thch "3")
	 (setvar "hpname" "telha3")
	 (setq cb4_hch_maisang 0
	       cb4_hch_scale 1.0
	 )
	)
	((= cbt_var_thch "4")
	 (setvar "hpname" "telha4")
	 (setq cb4_hch_maisang 0
	       cb4_hch_scale 1.0
	 )
	)
	((= cbt_var_thch "5")
	 (setvar "hpname" "telha5")
	 (setq cb4_hch_maisang 0
	       cb4_hch_scale 1.0
	 )
	)
	((= cbt_var_thch "6")
	 (setvar "hpname" "telha6")
	 (setq cb4_hch_maisang 0
	       cb4_hch_scale 1.0
	 )
	)
	((= cbt_var_thch "7")
	 (setvar "hpname" "telha7")
	 (setq cb4_hch_maisang 0
	       cb4_hch_scale 1.0
	 )
	)
      )
      (cn7_verylayer cbt_layc_hcl 7)
      (setvar "cecolor" cbt_layc_hcc)
      (setvar "celtype" "bylayer")
      (command "._bhatch" "_s" ss_hatch1 "" "_p" ""
	       (* (distof cbt_var_fhch) cn7_blkscl cb4_hch_scale) ;escala
	       (+ cb4_hch_maisang (/ (* cb4_angbase 180.0) pi)) ; ângulo
	       "_a" "_s" "_o" "" ""
      )
      (command "._bhatch" "_s" ss_hatch2 "" "_p" ""
	       (* (distof cbt_var_fhch) cn7_blkscl cb4_hch_scale) ;escala
	       (+ (+ cb4_hch_maisang (/ (* cb4_angbase 180.0) pi)) 180) ; ângulo
	       "_a" "_s" "_o" "" ""
      )
      (command "._bhatch" "_s" ss_hatch3 "" "_p" ""
	       (* (distof cbt_var_fhch) cn7_blkscl cb4_hch_scale) ;escala
	       (+ (+ cb4_hch_maisang (/ (* cb4_angbase 180.0) pi)) 90) ; ângulo
	       "_a" "_s" "_o" "" ""
      )
      (command "._bhatch" "_s" ss_hatch4 "" "_p" ""
	       (* (distof cbt_var_fhch) cn7_blkscl cb4_hch_scale) ;escala
	       (+ (+ cb4_hch_maisang (/ (* cb4_angbase 180.0) pi)) 270) ; ângulo
	       "_a" "_s" "_o" "" ""
      )
    )
  )
  (devolve)
  (prompt "\nUse o comando <UB> para retornar... ")
  (princ)
)

;desenho da cobertura tipo 05
;duas águas simples
(defun c:cb5 () (cbt_draw_05))

(defun cbt_draw_05 ()
  (setq ss_hatch1 (ssadd)
	ss_hatch2 (ssadd)
	ss_hatch3 (ssadd)
	ss_hatch4 (ssadd)
	ss_hatch5 (ssadd)
	ss_hatch6 (ssadd)
  )
  (guarda '("blipmode" "cecolor" "celtype" "clayer" "cmdecho" "orthomode"
          "textstyle" "luprec" "osmode" ))
  (cbt_layc_readfile)
  (setq cb5_pt0 (getpoint "\nClique no ponto base...")
	cb5_angbase (getangle cb5_pt0 "\nÂngulo para desenho...")
	cb5_pt1 (polar cb5_pt0 cb5_angbase (* cbt_fator (distof cbt_drw_c)))
	cb5_pt2 (polar cb5_pt1 (+ cb5_angbase (/ pi 2)) (* cbt_fator (- (distof cbt_drw_b) (distof cbt_drw_d))))
	cb5_pt3 (polar cb5_pt2 cb5_angbase (* cbt_fator (- (distof cbt_drw_a) (distof cbt_drw_c))))
	cb5_pt4 (polar cb5_pt3 (+ cb5_angbase (/ pi 2)) (* cbt_fator (distof cbt_drw_d)))
	cb5_pt5 (polar cb5_pt4 (+ cb5_angbase pi) (* cbt_fator (distof cbt_drw_a)))
	cb5_pt0a (polar cb5_pt0 (- cb5_angbase (/ pi 2)) (* cbt_fator (distof cbt_drw_p)))
	cb5_pt6 (polar cb5_pt0a (+ cb5_angbase pi) (* cbt_fator (distof cbt_drw_p)))
	cb5_pt7 (polar cb5_pt6 cb5_angbase (+ (* cbt_fator (distof cbt_drw_c)) (* 2.0 cbt_fator (distof cbt_drw_p))))
	cb5_pt8 (polar cb5_pt7 (+ cb5_angbase (/ pi 2)) (* cbt_fator (- (distof cbt_drw_b) (distof cbt_drw_d))))
	cb5_pt9 (polar cb5_pt8 cb5_angbase (* cbt_fator (- (distof cbt_drw_a) (distof cbt_drw_c))))
	cb5_pt10 (polar cb5_pt9 (+ cb5_angbase (/ pi 2))
			(+ (* cbt_fator (distof cbt_drw_d)) (* 2.0 cbt_fator (distof cbt_drw_p))))
	cb5_pt11 (polar cb5_pt10 (+ cb5_angbase pi)
			(+ (* cbt_fator (distof cbt_drw_a)) (* 2.0 cbt_fator (distof cbt_drw_p))))
	cb5_pt6a (polar cb5_pt6 cb5_angbase (/ (distance cb5_pt6 cb5_pt7) 2)) 
	cb5_pt12 (polar cb5_pt6a (+ cb5_angbase (/ pi 2)) (/ (distance cb5_pt6 cb5_pt7) 2))
	cb5_pt11a (polar cb5_pt11 (- cb5_angbase (/ pi 2)) (/ (distance cb5_pt9 cb5_pt10) 2))
	cb5_pt13 (polar cb5_pt11a cb5_angbase (/ (distance cb5_pt6 cb5_pt7) 2))
	cb5_pt9a (polar cb5_pt9 (+ cb5_angbase (/ pi 2)) (/ (distance cb5_pt9 cb5_pt10) 2))
	cb5_pt14 (polar cb5_pt9a (+ cb5_angbase pi) (/ (distance cb5_pt9 cb5_pt10) 2))
	cb5_pt15 (polar cb5_pt6a (+ cb5_angbase (/ pi 2)) (/ (distance cb5_pt9 cb5_pt10) 4))
	cb5_pt16 (polar cb5_pt12 (angle cb5_pt12 cb5_pt8) (/ (distance cb5_pt12 cb5_pt8) 2))
	cb5_pt17 (polar cb5_pt8 (angle cb5_pt8 cb5_pt14) (/ (distance cb5_pt14 cb5_pt8) 2))
	cb5_pt18 (polar cb5_pt14 cb5_angbase (/ (distance cb5_pt9 cb5_pt10) 4))
	cb5_pt13a (polar cb5_pt13 cb5_angbase (/ (distance cb5_pt14 cb5_pt13) 2))
	cb5_pt19 (polar cb5_pt13a (+ cb5_angbase (/ pi 2)) (/ (distance cb5_pt9 cb5_pt10) 4))
	cb5_pt12a (polar cb5_pt12 (+ cb5_angbase (/ pi 2)) (/ (distance cb5_pt12 cb5_pt13) 2))
	cb5_pt20 (polar cb5_pt12a (+ cb5_angbase pi) (/ (distance cb5_pt6 cb5_pt7) 4))
  )
  (setq grp_type "2")
  (cn7_find_blkscl)
  (command "._undo" "_m")
  ;Desenha a Projeção da Edificação
  (cn7_verylayer cbt_layc_edl 7)
  (setvar "cecolor" cbt_layc_edc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" cb5_pt0 "_non" cb5_pt1 "_non" cb5_pt2 "_non" cb5_pt3 "_non" cb5_pt4 "_non" cb5_pt5 "_c")
  ;desenha o contorno da cobertura
  (cn7_verylayer cbt_layc_cbl 7)
  (setvar "cecolor" cbt_layc_cbc)
  (setvar "celtype" "bylayer")
  (command "._line" "_non" cb5_pt6 "_non" cb5_pt7 "")
  (setq ss_hatch1 (ssadd (entlast) ss_hatch1))
  (command "._line" "_non" cb5_pt7 "_non" cb5_pt8 "")
  (setq ss_hatch2 (ssadd (entlast) ss_hatch2))
  (command "._line" "_non" cb5_pt8 "_non" cb5_pt9 "")
  (setq ss_hatch3 (ssadd (entlast) ss_hatch3))
  (command "._line" "_non" cb5_pt9 "_non" cb5_pt10 "")
  (setq ss_hatch4 (ssadd (entlast) ss_hatch4))
  (command "._line" "_non" cb5_pt10 "_non" cb5_pt11 "")
  (setq ss_hatch5 (ssadd (entlast) ss_hatch5))
  (command "._line" "_non" cb5_pt11 "_non" cb5_pt6 "")
  (setq ss_hatch6 (ssadd (entlast) ss_hatch6))
  (command "._line" "_non" cb5_pt6 "_non" cb5_pt12 "")
  (setq ss_hatch1 (ssadd (entlast) ss_hatch1))
  (setq ss_hatch6 (ssadd (entlast) ss_hatch6))
  (command "._line" "_non" cb5_pt7 "_non" cb5_pt12 "")
  (setq ss_hatch1 (ssadd (entlast) ss_hatch1))
  (setq ss_hatch2 (ssadd (entlast) ss_hatch2))
  (command "._line" "_non" cb5_pt8 "_non" cb5_pt13 "")
  (setq ss_hatch2 (ssadd (entlast) ss_hatch2))
  (setq ss_hatch3 (ssadd (entlast) ss_hatch3))
  (command "._line" "_non" cb5_pt9 "_non" cb5_pt14 "")
  (setq ss_hatch3 (ssadd (entlast) ss_hatch3))
  (setq ss_hatch4 (ssadd (entlast) ss_hatch4))
  (command "._line" "_non" cb5_pt10 "_non" cb5_pt14 "")
  (setq ss_hatch4 (ssadd (entlast) ss_hatch4))
  (setq ss_hatch5 (ssadd (entlast) ss_hatch5))
  (command "._line" "_non" cb5_pt11 "_non" cb5_pt13 "")
  (setq ss_hatch5 (ssadd (entlast) ss_hatch5))
  (setq ss_hatch6 (ssadd (entlast) ss_hatch6))
  (command "._line" "_non" cb5_pt12 "_non" cb5_pt13 "")
  (setq ss_hatch2 (ssadd (entlast) ss_hatch2))
  (setq ss_hatch6 (ssadd (entlast) ss_hatch6))
  (command "._line" "_non" cb5_pt13 "_non" cb5_pt14 "")
  (setq ss_hatch3 (ssadd (entlast) ss_hatch3))
  (setq ss_hatch5 (ssadd (entlast) ss_hatch5))
  ;insere a seta
  (if (= cbt_var_dset "1")
    (progn
      (setq cb5_setang (/ (* cb5_angbase 180) pi))
      (command "._insert" (strcat cnp_root "/blocos/cbt_seta_" cbt_var_tset ".dwg")
	       "_s" (* cbt_blkscl (distof cbt_var_fset)) "_non" cb5_pt15 (- cb5_setang 90))
      (setq ss_hatch1 (ssadd (entlast) ss_hatch1))
      (command "._insert" (strcat cnp_root "/blocos/cbt_seta_" cbt_var_tset ".dwg")
	       "_s" (* cbt_blkscl (distof cbt_var_fset)) "_non" cb5_pt16 cb5_setang)
      (setq ss_hatch2 (ssadd (entlast) ss_hatch2))
      (command "._insert" (strcat cnp_root "/blocos/cbt_seta_" cbt_var_tset ".dwg")
	       "_s" (* cbt_blkscl (distof cbt_var_fset)) "_non" cb5_pt17 (- cb5_setang 90))
      (setq ss_hatch3 (ssadd (entlast) ss_hatch3))
      (command "._insert" (strcat cnp_root "/blocos/cbt_seta_" cbt_var_tset ".dwg")
	       "_s" (* cbt_blkscl (distof cbt_var_fset)) "_non" cb5_pt18 cb5_setang)
      (setq ss_hatch4 (ssadd (entlast) ss_hatch4))
      (command "._insert" (strcat cnp_root "/blocos/cbt_seta_" cbt_var_tset ".dwg")
	       "_s" (* cbt_blkscl (distof cbt_var_fset)) "_non" cb5_pt19 (+ 90 cb5_setang))
      (setq ss_hatch5 (ssadd (entlast) ss_hatch5))
      (command "._insert" (strcat cnp_root "/blocos/cbt_seta_" cbt_var_tset ".dwg")
	       "_s" (* cbt_blkscl (distof cbt_var_fset)) "_non" cb5_pt20 (+ 180 cb5_setang))
      (setq ss_hatch6 (ssadd (entlast) ss_hatch6))
    )
  )
  ;desenha a hachura
  (if (= cbt_var_dhch "1")
    (progn
      (cond
	((= cbt_var_thch "0")
	 (setvar "hpname" "ansi31")
	 (setq cb5_hch_maisang 45
	       cb5_hch_scale 0.25
	 )
	)
	((= cbt_var_thch "1")
	 (setvar "hpname" "telha1")
	 (setq cb5_hch_maisang 0
	       cb5_hch_scale 1.0
	 )
	)
	((= cbt_var_thch "2")
	 (setvar "hpname" "telha2")
	 (setq cb5_hch_maisang 0
	       cb5_hch_scale 1.0
	 )
	)
	((= cbt_var_thch "3")
	 (setvar "hpname" "telha3")
	 (setq cb5_hch_maisang 0
	       cb5_hch_scale 1.0
	 )
	)
	((= cbt_var_thch "4")
	 (setvar "hpname" "telha4")
	 (setq cb5_hch_maisang 0
	       cb5_hch_scale 1.0
	 )
	)
	((= cbt_var_thch "5")
	 (setvar "hpname" "telha5")
	 (setq cb5_hch_maisang 0
	       cb5_hch_scale 1.0
	 )
	)
	((= cbt_var_thch "6")
	 (setvar "hpname" "telha6")
	 (setq cb5_hch_maisang 0
	       cb5_hch_scale 1.0
	 )
	)
	((= cbt_var_thch "7")
	 (setvar "hpname" "telha7")
	 (setq cb5_hch_maisang 0
	       cb5_hch_scale 1.0
	 )
	)
      )
      (cn7_verylayer cbt_layc_hcl 7)
      (setvar "cecolor" cbt_layc_hcc)
      (setvar "celtype" "bylayer")
      (command "._bhatch" "_s" ss_hatch1 "" "_p" ""
	       (* (distof cbt_var_fhch) cn7_blkscl cb5_hch_scale) ;escala
	       (+ cb5_hch_maisang (/ (* cb5_angbase 180.0) pi)) ; ângulo
	       "_a" "_s" "_o" "" ""
      )
      (command "._bhatch" "_s" ss_hatch2 "" "_p" ""
	       (* (distof cbt_var_fhch) cn7_blkscl cb5_hch_scale) ;escala
	       (+ (+ cb5_hch_maisang (/ (* cb5_angbase 180.0) pi)) 90) ; ângulo
	       "_a" "_s" "_o" "" ""
      )
      (command "._bhatch" "_s" ss_hatch3 "" "_p" ""
	       (* (distof cbt_var_fhch) cn7_blkscl cb5_hch_scale) ;escala
	       (+ (+ cb5_hch_maisang (/ (* cb5_angbase 180.0) pi)) 0) ; ângulo
	       "_a" "_s" "_o" "" ""
      )
      (command "._bhatch" "_s" ss_hatch4 "" "_p" ""
	       (* (distof cbt_var_fhch) cn7_blkscl cb5_hch_scale) ;escala
	       (+ (+ cb5_hch_maisang (/ (* cb5_angbase 180.0) pi)) 90) ; ângulo
	       "_a" "_s" "_o" "" ""
      )
      (command "._bhatch" "_s" ss_hatch5 "" "_p" ""
	       (* (distof cbt_var_fhch) cn7_blkscl cb5_hch_scale) ;escala
	       (+ (+ cb5_hch_maisang (/ (* cb5_angbase 180.0) pi)) 180) ; ângulo
	       "_a" "_s" "_o" "" ""
      )
      (command "._bhatch" "_s" ss_hatch6 "" "_p" ""
	       (* (distof cbt_var_fhch) cn7_blkscl cb5_hch_scale) ;escala
	       (+ (+ cb5_hch_maisang (/ (* cb5_angbase 180.0) pi)) 270) ; ângulo
	       "_a" "_s" "_o" "" ""
      )
    )
  )
  (devolve)
  (prompt "\nUse o comando <UB> para retornar... ")
  (princ)
)


;desenho da cobertura tipo 06
;duas águas simples
(defun c:cb6 () (cbt_draw_06))

(defun cbt_draw_06 ()
  (setq ss_hatch1 (ssadd)
	ss_hatch2 (ssadd)
	ss_hatch3 (ssadd)
	ss_hatch4 (ssadd)
	ss_hatch5 (ssadd)
	ss_hatch6 (ssadd)
	ss_hatch7 (ssadd)
  )
  (guarda '("blipmode" "cecolor" "celtype" "clayer" "cmdecho" "orthomode"
          "textstyle" "luprec" "osmode" ))
  (cbt_layc_readfile)
  (setq cb6_pt0 (getpoint "\nClique no ponto base...")
	cb6_angbase (getangle cb6_pt0 "\nÂngulo para desenho...")
	cb6_pt1 (polar cb6_pt0 cb6_angbase (* cbt_fator (distof cbt_drw_b)))
	cb6_pt2 (polar cb6_pt1 (+ cb6_angbase (/ pi 2)) (* cbt_fator (distof cbt_drw_c)))
	cb6_pt3 (polar cb6_pt2 cb6_angbase (* cbt_fator (- (distof cbt_drw_a) (distof cbt_drw_b) (distof cbt_drw_e))))
	cb6_pt4 (polar cb6_pt3 (+ cb6_angbase (/ pi 2)) (* cbt_fator (distof cbt_drw_d)))
	cb6_pt5 (polar cb6_pt4 (+ cb6_angbase pi) (* cbt_fator (distof cbt_drw_a)))
	cb6_pt6 (polar cb6_pt5 (- cb6_angbase (/ pi 2)) (* cbt_fator (distof cbt_drw_d)))
	cb6_pt7 (polar cb6_pt6 cb6_angbase (* cbt_fator (distof cbt_drw_e)))
	cb6_pt0a (polar cb6_pt0 (- cb6_angbase (/ pi 2)) (* cbt_fator (distof cbt_drw_p)))
	cb6_pt8 (polar cb6_pt0a (+ cb6_angbase pi) (* cbt_fator (distof cbt_drw_p)))
	cb6_pt9 (polar cb6_pt8 cb6_angbase (+ (* cbt_fator (distof cbt_drw_b)) (* 2.0 cbt_fator (distof cbt_drw_p))))
	cb6_pt10 (polar cb6_pt9 (+ cb6_angbase (/ pi 2)) (* cbt_fator (distof cbt_drw_c)))
	cb6_pt11 (polar cb6_pt10 cb6_angbase (* cbt_fator (- (distof cbt_drw_a) (distof cbt_drw_b) (distof cbt_drw_e))))
	cb6_pt12 (polar cb6_pt11 (+ cb6_angbase (/ pi 2))
			(+ (* cbt_fator (distof cbt_drw_d)) (* 2.0 cbt_fator (distof cbt_drw_p))))
	cb6_pt13 (polar cb6_pt12 (+ cb6_angbase pi)
			(+ (* cbt_fator (distof cbt_drw_a)) (* 2.0 cbt_fator (distof cbt_drw_p))))
	cb6_pt14 (polar cb6_pt13 (- cb6_angbase (/ pi 2))
			(+ (* cbt_fator (distof cbt_drw_d)) (* 2.0 cbt_fator (distof cbt_drw_p))))
	cb6_pt15 (polar cb6_pt14 cb6_angbase (* cbt_fator (distof cbt_drw_e)))
	cb6_pt8a (polar cb6_pt8 cb6_angbase (/ (distance cb6_pt8 cb6_pt9) 2))
	cb6_pt16 (polar cb6_pt8a (+ cb6_angbase (/ pi 2)) (/ (distance cb6_pt8 cb6_pt9) 2))
	cb6_pt17 (polar cb6_pt15 (angle cb6_pt15 cb6_pt10) (/ (distance cb6_pt15 cb6_pt10) 2))
	cb6_pt13a (polar cb6_pt13 cb6_angbase (/ (distance cb6_pt13 cb6_pt14) 2))
	cb6_pt18 (polar cb6_pt13a (- cb6_angbase (/ pi 2)) (/ (distance cb6_pt13 cb6_pt14) 2))
	cb6_pt12a (polar cb6_pt12 (+ cb6_angbase pi) (/ (distance cb6_pt13 cb6_pt14) 2))
	cb6_pt19 (polar cb6_pt12a (- cb6_angbase (/ pi 2)) (/ (distance cb6_pt13 cb6_pt14) 2))
	cb6_pt20 (polar cb6_pt16 (- cb6_angbase (/ pi 2)) (/ (distance cb6_pt13 cb6_pt14) 4))
	cb6_pt16a (polar cb6_pt16 (+ cb6_angbase (/ pi 2)) (/ (distance cb6_pt16 cb6_pt17) 2))
	cb6_pt21 (polar cb6_pt16a cb6_angbase (/ (distance cb6_pt10 cb6_pt17) 2))
	cb6_pt22 (polar cb6_pt16a (+ cb6_angbase pi) (/ (distance cb6_pt15 cb6_pt17) 2))
	cb6_pt18a (polar cb6_pt18 cb6_angbase (/ (distance cb6_pt18 cb6_pt19) 2))
	cb6_pt23 (polar cb6_pt18a (- cb6_angbase (/ pi 2)) (/ (distance cb6_pt11 cb6_pt12) 4))
	cb6_pt24 (polar cb6_pt19 cb6_angbase (/ (distance cb6_pt11 cb6_pt12) 4))
	cb6_pt25 (polar cb6_pt18a (+ cb6_angbase (/ pi 2)) (/ (distance cb6_pt11 cb6_pt12) 4))
	cb6_pt26 (polar cb6_pt18 (+ cb6_angbase pi) (/ (distance cb6_pt13 cb6_pt14) 4))
  )
  (setq grp_type "2")
  (cn7_find_blkscl)
  (command "._undo" "_m")
  ;Desenha a Projeção da Edificação
  (cn7_verylayer cbt_layc_edl 7)
  (setvar "cecolor" cbt_layc_edc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" cb6_pt0 "_non" cb6_pt1 "_non" cb6_pt2 "_non" cb6_pt3 "_non" cb6_pt4
	   "_non" cb6_pt5  "_non" cb6_pt6  "_non" cb6_pt7 "_c")
  ;desenha o contorno da cobertura
  (cn7_verylayer cbt_layc_cbl 7)
  (setvar "cecolor" cbt_layc_cbc)
  (setvar "celtype" "bylayer")
  (command "._line" "_non" cb6_pt8 "_non" cb6_pt9 "")
  (setq ss_hatch1 (ssadd (entlast) ss_hatch1))
  (command "._line" "_non" cb6_pt9 "_non" cb6_pt10 "")
  (setq ss_hatch2 (ssadd (entlast) ss_hatch2))
  (command "._line" "_non" cb6_pt10 "_non" cb6_pt11 "")
  (setq ss_hatch4 (ssadd (entlast) ss_hatch4))
  (command "._line" "_non" cb6_pt11 "_non" cb6_pt12 "")
  (setq ss_hatch5 (ssadd (entlast) ss_hatch5))
  (command "._line" "_non" cb6_pt12 "_non" cb6_pt13 "")
  (setq ss_hatch6 (ssadd (entlast) ss_hatch6))
  (command "._line" "_non" cb6_pt13 "_non" cb6_pt14 "")
  (setq ss_hatch7 (ssadd (entlast) ss_hatch7))
  (command "._line" "_non" cb6_pt14 "_non" cb6_pt15 "")
  (setq ss_hatch4 (ssadd (entlast) ss_hatch4))
  (command "._line" "_non" cb6_pt15 "_non" cb6_pt8 "")
  (setq ss_hatch3 (ssadd (entlast) ss_hatch3))
  (command "._line" "_non" cb6_pt16 "_non" cb6_pt8 "")
  (setq ss_hatch1 (ssadd (entlast) ss_hatch1))
  (setq ss_hatch3 (ssadd (entlast) ss_hatch3))
  (command "._line" "_non" cb6_pt16 "_non" cb6_pt9 "")
  (setq ss_hatch1 (ssadd (entlast) ss_hatch1))
  (setq ss_hatch2 (ssadd (entlast) ss_hatch2))
  (command "._line" "_non" cb6_pt16 "_non" cb6_pt17 "")
  (setq ss_hatch2 (ssadd (entlast) ss_hatch2))
  (setq ss_hatch3 (ssadd (entlast) ss_hatch3))
  (command "._line" "_non" cb6_pt15 "_non" cb6_pt17 "")
  (setq ss_hatch3 (ssadd (entlast) ss_hatch3))
  (setq ss_hatch4 (ssadd (entlast) ss_hatch4))
  (command "._line" "_non" cb6_pt10 "_non" cb6_pt17 "")
  (setq ss_hatch2 (ssadd (entlast) ss_hatch2))
  (setq ss_hatch4 (ssadd (entlast) ss_hatch4))
  (command "._line" "_non" cb6_pt18 "_non" cb6_pt14 "")
  (setq ss_hatch4 (ssadd (entlast) ss_hatch4))
  (setq ss_hatch7 (ssadd (entlast) ss_hatch7))
  (command "._line" "_non" cb6_pt18 "_non" cb6_pt13 "")
  (setq ss_hatch6 (ssadd (entlast) ss_hatch6))
  (setq ss_hatch7 (ssadd (entlast) ss_hatch7))
  (command "._line" "_non" cb6_pt18 "_non" cb6_pt19 "")
  (setq ss_hatch4 (ssadd (entlast) ss_hatch4))
  (setq ss_hatch6 (ssadd (entlast) ss_hatch6))
  (command "._line" "_non" cb6_pt12 "_non" cb6_pt19 "")
  (setq ss_hatch5 (ssadd (entlast) ss_hatch5))
  (setq ss_hatch6 (ssadd (entlast) ss_hatch6))
  (command "._line" "_non" cb6_pt11 "_non" cb6_pt19 "")
  (setq ss_hatch4 (ssadd (entlast) ss_hatch4))
  (setq ss_hatch5 (ssadd (entlast) ss_hatch5))
  ;insere a seta
  (if (= cbt_var_dset "1")
    (progn
      (setq cb6_setang (/ (* cb6_angbase 180) pi))
      (command "._insert" (strcat cnp_root "/blocos/cbt_seta_" cbt_var_tset ".dwg")
	       "_s" (* cbt_blkscl (distof cbt_var_fset)) "_non" cb6_pt20 (- cb6_setang 90))
      (setq ss_hatch1 (ssadd (entlast) ss_hatch1))
      (command "._insert" (strcat cnp_root "/blocos/cbt_seta_" cbt_var_tset ".dwg")
	       "_s" (* cbt_blkscl (distof cbt_var_fset)) "_non" cb6_pt21 cb6_setang)
      (setq ss_hatch2 (ssadd (entlast) ss_hatch2))
      (command "._insert" (strcat cnp_root "/blocos/cbt_seta_" cbt_var_tset ".dwg")
	       "_s" (* cbt_blkscl (distof cbt_var_fset)) "_non" cb6_pt22 (- cb6_setang 180))
      (setq ss_hatch3 (ssadd (entlast) ss_hatch3))
      (command "._insert" (strcat cnp_root "/blocos/cbt_seta_" cbt_var_tset ".dwg")
	       "_s" (* cbt_blkscl (distof cbt_var_fset)) "_non" cb6_pt23 (- 90 cb6_setang))
      (setq ss_hatch4 (ssadd (entlast) ss_hatch4))
      (command "._insert" (strcat cnp_root "/blocos/cbt_seta_" cbt_var_tset ".dwg")
	       "_s" (* cbt_blkscl (distof cbt_var_fset)) "_non" cb6_pt24 cb6_setang)
      (setq ss_hatch5 (ssadd (entlast) ss_hatch5))
      (command "._insert" (strcat cnp_root "/blocos/cbt_seta_" cbt_var_tset ".dwg")
	       "_s" (* cbt_blkscl (distof cbt_var_fset)) "_non" cb6_pt25 (+ 90 cb6_setang))
      (setq ss_hatch6 (ssadd (entlast) ss_hatch6))
      (command "._insert" (strcat cnp_root "/blocos/cbt_seta_" cbt_var_tset ".dwg")
	       "_s" (* cbt_blkscl (distof cbt_var_fset)) "_non" cb6_pt26 (+ 180 cb6_setang))
      (setq ss_hatch7 (ssadd (entlast) ss_hatch7))
    )
  )
  ;desenha a hachura
  (if (= cbt_var_dhch "1")
    (progn
      (cond
	((= cbt_var_thch "0")
	 (setvar "hpname" "ansi31")
	 (setq cb6_hch_maisang 45
	       cb6_hch_scale 0.25
	 )
	)
	((= cbt_var_thch "1")
	 (setvar "hpname" "telha1")
	 (setq cb6_hch_maisang 0
	       cb6_hch_scale 1.0
	 )
	)
	((= cbt_var_thch "2")
	 (setvar "hpname" "telha2")
	 (setq cb6_hch_maisang 0
	       cb6_hch_scale 1.0
	 )
	)
	((= cbt_var_thch "3")
	 (setvar "hpname" "telha3")
	 (setq cb6_hch_maisang 0
	       cb6_hch_scale 1.0
	 )
	)
	((= cbt_var_thch "4")
	 (setvar "hpname" "telha4")
	 (setq cb6_hch_maisang 0
	       cb6_hch_scale 1.0
	 )
	)
	((= cbt_var_thch "5")
	 (setvar "hpname" "telha5")
	 (setq cb6_hch_maisang 0
	       cb6_hch_scale 1.0
	 )
	)
	((= cbt_var_thch "6")
	 (setvar "hpname" "telha6")
	 (setq cb6_hch_maisang 0
	       cb6_hch_scale 1.0
	 )
	)
	((= cbt_var_thch "7")
	 (setvar "hpname" "telha7")
	 (setq cb6_hch_maisang 0
	       cb6_hch_scale 1.0
	 )
	)
      )
      (cn7_verylayer cbt_layc_hcl 7)
      (setvar "cecolor" cbt_layc_hcc)
      (setvar "celtype" "bylayer")
      (command "._bhatch" "_s" ss_hatch1 "" "_p" ""
	       (* (distof cbt_var_fhch) cn7_blkscl cb6_hch_scale) ;escala
	       (+ cb6_hch_maisang (/ (* cb6_angbase 180.0) pi)) ; ângulo
	       "_a" "_s" "_o" "" ""
      )
      (command "._bhatch" "_s" ss_hatch2 "" "_p" ""
	       (* (distof cbt_var_fhch) cn7_blkscl cb6_hch_scale) ;escala
	       (+ (+ cb6_hch_maisang (/ (* cb6_angbase 180.0) pi)) 90) ; ângulo
	       "_a" "_s" "_o" "" ""
      )
      (command "._bhatch" "_s" ss_hatch3 "" "_p" ""
	       (* (distof cbt_var_fhch) cn7_blkscl cb6_hch_scale) ;escala
	       (+ (+ cb6_hch_maisang (/ (* cb6_angbase 180.0) pi)) 270) ; ângulo
	       "_a" "_s" "_o" "" ""
      )
      (command "._bhatch" "_s" ss_hatch4 "" "_p" ""
	       (* (distof cbt_var_fhch) cn7_blkscl cb6_hch_scale) ;escala
	       (+ (+ cb6_hch_maisang (/ (* cb6_angbase 180.0) pi)) 0) ; ângulo
	       "_a" "_s" "_o" "" ""
      )
      (command "._bhatch" "_s" ss_hatch5 "" "_p" ""
	       (* (distof cbt_var_fhch) cn7_blkscl cb6_hch_scale) ;escala
	       (+ (+ cb6_hch_maisang (/ (* cb6_angbase 180.0) pi)) 90) ; ângulo
	       "_a" "_s" "_o" "" ""
      )
      (command "._bhatch" "_s" ss_hatch6 "" "_p" ""
	       (* (distof cbt_var_fhch) cn7_blkscl cb6_hch_scale) ;escala
	       (+ (+ cb6_hch_maisang (/ (* cb6_angbase 180.0) pi)) 180) ; ângulo
	       "_a" "_s" "_o" "" ""
      )
      (command "._bhatch" "_s" ss_hatch7 "" "_p" ""
	       (* (distof cbt_var_fhch) cn7_blkscl cb6_hch_scale) ;escala
	       (+ (+ cb6_hch_maisang (/ (* cb6_angbase 180.0) pi)) 270) ; ângulo
	       "_a" "_s" "_o" "" ""
      )
    )
  )
  (devolve)
  (prompt "\nUse o comando <UB> para retornar... ")
  (princ)
)


;cnp_21_c

;progama de geração de escadas
;iniciado em 11/02/11
;Denio Guimarães
;www.cadnorma.com.br
(defun c:scd ()
  (scd_start)
  (setq dcl_id (load_dialog (strcat cnp_root "/lisp/cadnorma.dcl")))
  (if (not (new_dialog "scd" dcl_id)) (exit))
  ;atualiza os slides
  (setq x (dimx_tile "scd_slide1")
	y (dimy_tile "scd_slide1"))
  (start_image "scd_slide1")
  (fill_image 0 0 x y -2)
  (slide_image 0 0 x y (strcat cnp_root "/slides/sc1.sld"))
  (end_image)
  (setq x (dimx_tile "scd_slide2")
	y (dimy_tile "scd_slide2"))
  (start_image "scd_slide2")
  (fill_image 0 0 x y -2)
  (slide_image 0 0 x y (strcat cnp_root "/slides/sc2.sld"))
  (end_image)
  (setq x (dimx_tile "scd_slide3")
	y (dimy_tile "scd_slide3"))
  (start_image "scd_slide3")
  (fill_image 0 0 x y -2)
  (slide_image 0 0 x y (strcat cnp_root "/slides/sc3.sld"))
  (end_image)
  ;atualização do texto
  (cond
    ((= scd_type "1") (set_tile "scd_text" "Escada Reta em Planta Baixa"))
    ((= scd_type "2") (set_tile "scd_text" "Escada Reta em Vista"))
    ((= scd_type "3") (set_tile "scd_text" "Escada Circular em Planta Baixa"))
  )
  ;ações dos botões
  (action_tile "scd_slide1" "(scd_uptext1)")
  (action_tile "scd_slide2" "(scd_uptext2)")
  (action_tile "scd_slide3" "(scd_uptext3)")
  ;comandos gerais
  (action_tile "cancel" "(done_dialog 0)")
  (action_tile "accept" "(done_dialog 1)")
  ;ativação da DCL
  (setq scd_dcl_id (start_dialog))
  (unload_dialog dcl_id)
  (if (= 1 scd_dcl_id) (scd_ok))
)

;direciona para a escada escolhida
(defun scd_ok ()
  (scd_last_writefile)
  (cond
    ((= scd_type "1") (scd11_main))
    ((= scd_type "2") (scd13_main))
    ((= scd_type "3") (scd12_main))
  )
)

;ao selecionar o slide1
(defun scd_uptext1 ()
  (setq scd_type "1")
  (set_tile "scd_text" "Escada Reta em Planta Baixa")
)

;ao selecionar o slide2
(defun scd_uptext2 ()
  (setq scd_type "2")
  (set_tile "scd_text" "Escada Reta em Vista")
)
;ao selecionar o slide1
(defun scd_uptext3 ()
  (setq scd_type "3")
  (set_tile "scd_text" "Escada Circular em Planta Baixa")
)

;lê os dados iniciais da DCL no arquivo de dados
(defun scd_last_file ()
  (if (findfile (strcat cnp_root "/config/scd_last.txt"))
    (scd_last_readfile)
    (progn
      (setq file (open (strcat cnp_root "/config/scd_last.txt") "w" "utf8"))
      (write-line "1" file)
      (close file)
      (scd_last_readfile)
    )
  )
)

;função que lê o arquivo de dados
(defun scd_last_readfile ()
  (setq	file (open (strcat cnp_root "/config/scd_last.txt") "r" "utf8"))
  (setq	scd_type (read-line file))
  (close file)
)

;função que escreve o arquivo de dados
(defun scd_last_writefile ()
  (setq	file (open (strcat cnp_root "/config/scd_last.txt") "w" "utf8"))
  (write-line scd_type file)
  (close file)
)


;procedimento inicial para escadas
(defun scd_start ()
  (cn7_init)
  (guarda '("blipmode" "cecolor" "celtype" "clayer" "cmdecho" "orthomode"
          "textstyle" "luprec" "osmode" ))
  (setvar "cecolor" "bylayer")
  (scd_last_file)
  (cond
    ((= cn7_dwgunit 1) (setq scd_fator 0.01 scd_blkscl 1.0))
    ((= cn7_dwgunit 100) (setq scd_fator 1.0 scd_blkscl 100.0))
    ((= cn7_dwgunit 1000) (setq scd_fator 10.0 scd_blkscl 1000.0))
  )
)

;desenho de escada simples
(defun c:sc1 () (scd11_main))

(defun scd11_main ()
  (scd11_start)
  (setq dcl_id (load_dialog (strcat cnp_root "/lisp/cadnorma.dcl")))
  (if (not (new_dialog "scd11" dcl_id)) (exit))
  (set_tile "scd11_vis_radio" scd11_var_svis)
  (action_tile "scd11_vis_radio" "(scd11_radio)")
  ;slide
  (scd11_upslide)
  ;dados de  construção
  (set_tile "scd11_getlarg" scd11_var_larg)
  (action_tile "scd11_getlarg" "(scd11_getlarg_action)")
  (action_tile "scd11_piklarg" "(done_dialog 2)")
  (set_tile "scd11_getndeg" scd11_var_ndeg)
  (action_tile "scd11_getndeg" "(scd11_getndeg_action)")
  (set_tile "scd11_getldeg" scd11_var_ldeg)
  (action_tile "scd11_getldeg" "(scd11_getldeg_action)")
  (action_tile "scd11_pikldeg" "(done_dialog 3)")
  ;toggles
  (set_tile "scd11_getlind" scd11_var_lind)
  (action_tile "scd11_getlind" "(setq scd11_var_lind $value)")
  (set_tile "scd11_getline" scd11_var_line)
  (action_tile "scd11_getline" "(setq scd11_var_line $value)")
  (set_tile "scd11_getcord" scd11_var_cord)
  (action_tile "scd11_getcord" "(setq scd11_var_cord $value)")
  (set_tile "scd11_getcore" scd11_var_core)
  (action_tile "scd11_getcore" "(setq scd11_var_core $value)")
  ;cores e layers
  (action_tile "scd11_cfglayc" "(done_dialog 4)")
  ;comandos gerais
  (action_tile "cancel" "(done_dialog 0)")
  (action_tile "accept" "(done_dialog 1)")
  ;ativação da DCL
  (setq scd11_dcl_id (start_dialog))
  (unload_dialog dcl_id)
  ;ações dos botões
  (if (= 1 scd11_dcl_id) (scd11_ok_action))
  (if (= 2 scd11_dcl_id) (scd11_getlarg_button))
  (if (= 3 scd11_dcl_id) (scd11_getldeg_button))
  (if (= 4 scd11_dcl_id) (scd11_laycol_button))
)

;decide o tipo de escada que vai desenhar
(defun scd11_ok_action ()
  (cond
    ((= scd11_var_svis "scd11_vis_01") (scd11_draw_01))
    ((= scd11_var_svis "scd11_vis_02") (scd11_draw_02))
    ((= scd11_var_svis "scd11_vis_03") (scd11_draw_03))
  )
)

;desenha a escada totalmente em projeção
(defun scd11_draw_03 ()
  (command "._undo" "_m")
  (cn7_verylayer scd11_layc_dpl 7)
  (setvar "cecolor" scd11_layc_dpc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (scd11_last_writefile)
  (setq scd11_pt0 (getpoint "\nClique no ponto inicial...")
	scd11_angbase (getangle scd11_pt0 "\nDireção da escada...")
        scd11_angorto (+ scd11_angbase (/ pi 2))
	pt1 scd11_pt0
	pt2 (polar pt1 scd11_angorto (* scd11_fator (distof scd11_var_larg)))
	cord_pt1 (polar pt1 scd11_angorto (* scd11_fator 5.0))
	core_pt1 (polar pt2 (+ scd11_angorto pi) (* scd11_fator 5.0))
  )
  (command "._line" "_non" pt1 "_non" pt2 "")
  (setq lind_pt1 pt1
	line_pt1 pt2
  )
  ;desenha os degraus
  (repeat (1- (fix (distof scd11_var_ndeg)))
    (setq pt1 (polar pt1 scd11_angbase (* scd11_fator (distof scd11_var_ldeg)))
	  pt2 (polar pt2 scd11_angbase (* scd11_fator (distof scd11_var_ldeg)))
    )
    (command "._line" "_non" pt1 "_non" pt2 "")
  )
  ;desenha os corrimãos
  (setq cord_pt2 (polar pt1 scd11_angorto (* scd11_fator 5.0))
	core_pt2 (polar pt2 (+ scd11_angorto pi) (* scd11_fator 5.0))
  )
  (if (= scd11_var_cord "1")
    (command "._line" "_non" cord_pt1 "_non" cord_pt2 "")
  )
  (if (= scd11_var_core "1")
    (command "._line" "_non" core_pt1 "_non" core_pt2 "")
  )
  ;desenha as linhas laterais
  (setq lind_pt2 pt1
	line_pt2 pt2
  )
  (if (= scd11_var_lind "1")
    (command "._line" "_non" lind_pt1 "_non" lind_pt2 "")
  )
  (if (= scd11_var_line "1")
    (command "._line" "_non" line_pt1 "_non" line_pt2 "")
  )
  (devolve)
  (prompt "\nDitite <UB> para retornar...")
  (princ)
)

;dese ha a escada interrompida (meio vista, meio rojeção)
(defun scd11_draw_02 ()
  (command "._undo" "_m")
  (scd11_last_writefile)
  (setq scd11_pt0 (getpoint "\nClique no ponto inicial...")
	scd11_angbase (getangle scd11_pt0 "\nDireção da escada...")
        scd11_angorto (+ scd11_angbase (/ pi 2))
	pt1 scd11_pt0
	pt2 (polar pt1 scd11_angorto (* scd11_fator (distof scd11_var_larg)))
	cord_pt1 (polar pt1 scd11_angorto (* scd11_fator 5.0))
	core_pt1 (polar pt2 (+ scd11_angorto pi) (* scd11_fator 5.0))
  )
  ;desenha os degraus em vista
  (cn7_verylayer scd11_layc_dvl 7)
  (setvar "cecolor" scd11_layc_dvc)
  (setvar "celtype" "bylayer")
  (command "._line" "_non" pt1 "_non" pt2 "")
  (setq lind_pt1 pt1
	line_pt1 pt2
  )
  (setq n (1- (fix (/ (distof scd11_var_ndeg) 2))))
  (repeat n
    (setq pt1 (polar pt1 scd11_angbase (* scd11_fator (distof scd11_var_ldeg)))
	  pt2 (polar pt2 scd11_angbase (* scd11_fator (distof scd11_var_ldeg)))
    )
    (command "._line" "_non" pt1 "_non" pt2 "")
  )
  ;define os pontos iniciais de interrupção e corrimão
  (setq pti1 pt1
	ptca (polar pt1 scd11_angorto (* 5 scd11_fator))
	ptc1 (polar ptca scd11_angbase (* scd11_fator (/ (* 10 (distof scd11_var_ldeg)) (distof scd11_var_larg))))
  )
  ;desenha o degrau de transição
  (setq pt1 (polar pt1 scd11_angbase (* scd11_fator (distof scd11_var_ldeg)))
	pt2 (polar pt2 scd11_angbase (* scd11_fator (distof scd11_var_ldeg)))
	ptm (polar pt1 (angle pt1 pt2) (/ (distance pt1 pt2) 2))
  )
  (command "._line" "_non" pt2 "_non" ptm "")
  ;desenha os degraus em projeção
  (cn7_verylayer scd11_layc_dpl 7)
  (setvar "cecolor" scd11_layc_dpc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._line" "_non" pt1 "_non" ptm "")
  (setq pt1 (polar pt1 scd11_angbase (* scd11_fator (distof scd11_var_ldeg)))
	pt2 (polar pt2 scd11_angbase (* scd11_fator (distof scd11_var_ldeg)))
	pti2 pt2
	ptcb (polar pt2 (+ scd11_angorto pi) (* 5 scd11_fator))
	ptc2 (polar ptcb (+ scd11_angbase pi) (* scd11_fator (/ (* 10 (distof scd11_var_ldeg)) (distof scd11_var_larg))))
  )
  (command "._line" "_non" pt1 "_non" pt2 "")
  (repeat (1- n)
    (setq pt1 (polar pt1 scd11_angbase (* scd11_fator (distof scd11_var_ldeg)))
	  pt2 (polar pt2 scd11_angbase (* scd11_fator (distof scd11_var_ldeg)))
    )
    (command "._line" "_non" pt1 "_non" pt2 "")
  )
  ;desenha a linha de interrupção
  (cn7_verylayer scd11_layc_itl 7)
  (setvar "cecolor" scd11_layc_itc)
  (if (not (tblsearch "ltype" "interrup"))
    (command "._linetype" "_l" "interrup" (strcat cnp_root "/modelos/cadnorma.lin") "")
    (command "._linetype" "_l" "interrup" (strcat cnp_root "/modelos/cadnorma.lin") "_y" "")
  )
  (setvar "celtype" "interrup")
  (command "._line" "_non" pti1 "_non" pti2 "")
  ;desenha os corrimãos
  (setq cord_pt2 (polar pt1 scd11_angorto (* scd11_fator 5.0))
	core_pt2 (polar pt2 (+ scd11_angorto pi) (* scd11_fator 5.0))
  )
  (if (= scd11_var_cord "1")
    (progn
      (cn7_verylayer scd11_layc_crl 7)
      (setvar "cecolor" scd11_layc_crc)
      (setvar "celtype" "bylayer")
      (command "._line" "_non" cord_pt1 "_non" ptc1 "")
      (cn7_verylayer scd11_layc_dpl 7)
      (setvar "cecolor" scd11_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
      (command "._line" "_non" ptc1 "_non" cord_pt2 "")
    )
  )
  (if (= scd11_var_core "1")
    (progn
      (cn7_verylayer scd11_layc_crl 7)
      (setvar "cecolor" scd11_layc_crc)
      (setvar "celtype" "bylayer")
      (command "._line" "_non" core_pt1 "_non" ptc2 "")
      (cn7_verylayer scd11_layc_dpl 7)
      (setvar "cecolor" scd11_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
      (command "._line" "_non" ptc2 "_non" core_pt2 "")
    )
  )
  ;desenha as linhas laterais
  (setq lind_pt2 pt1
	line_pt2 pt2
  )
  (if (= scd11_var_lind "1")
    (progn
      (cn7_verylayer scd11_layc_dvl 7)
      (setvar "cecolor" scd11_layc_dvc)
      (setvar "celtype" "bylayer")
      (command "._line" "_non" lind_pt1 "_non" pti1 "")
      (cn7_verylayer scd11_layc_dpl 7)
      (setvar "cecolor" scd11_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
      (command "._line" "_non" pti1 "_non" lind_pt2 "")
    )
  )
  (if (= scd11_var_line "1")
    (progn
      (cn7_verylayer scd11_layc_dvl 7)
      (setvar "cecolor" scd11_layc_dvc)
      (setvar "celtype" "bylayer")
      (command "._line" "_non" line_pt1 "_non" pti2 "")
      (cn7_verylayer scd11_layc_dpl 7)
      (setvar "cecolor" scd11_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
      (command "._line" "_non" pti2 "_non" line_pt2 "")
    )
  )
  (devolve)
  (prompt "\nDitite <UB> para retornar...")
  (princ)
)

;desenha a escada totalmente em vista
(defun scd11_draw_01 ()
  (command "._undo" "_m")
  (scd11_last_writefile)
  (setq scd11_pt0 (getpoint "\nClique no ponto inicial...")
	scd11_angbase (getangle scd11_pt0 "\nDireção da escada...")
        scd11_angorto (+ scd11_angbase (/ pi 2))
	pt1 scd11_pt0
	pt2 (polar pt1 scd11_angorto (* scd11_fator (distof scd11_var_larg)))
	cord_pt1 (polar pt1 scd11_angorto (* scd11_fator 5.0))
	core_pt1 (polar pt2 (+ scd11_angorto pi) (* scd11_fator 5.0))
  )
  (cn7_verylayer scd11_layc_dvl 7)
  (setvar "cecolor" scd11_layc_dvc)
  (setvar "celtype" "bylayer")
  (command "._line" "_non" pt1 "_non" pt2 "")
  (setq lind_pt1 pt1
	line_pt1 pt2
  )
  ;desenha os degraus
  (repeat (1- (fix (distof scd11_var_ndeg)))
    (setq pt1 (polar pt1 scd11_angbase (* scd11_fator (distof scd11_var_ldeg)))
	  pt2 (polar pt2 scd11_angbase (* scd11_fator (distof scd11_var_ldeg)))
    )
    (command "._line" "_non" pt1 "_non" pt2 "")
  )
  ;desenha os corrimãos
  (cn7_verylayer scd11_layc_crl 7)
  (setvar "cecolor" scd11_layc_crc)
  (setvar "celtype" "bylayer")
  (setq cord_pt2 (polar pt1 scd11_angorto (* scd11_fator 5.0))
	core_pt2 (polar pt2 (+ scd11_angorto pi) (* scd11_fator 5.0))
  )
  (if (= scd11_var_cord "1")
    (command "._line" "_non" cord_pt1 "_non" cord_pt2 "")
  )
  (if (= scd11_var_core "1")
    (command "._line" "_non" core_pt1 "_non" core_pt2 "")
  )
  ;desenha as linhas laterais
  (cn7_verylayer scd11_layc_dvl 7)
  (setvar "cecolor" scd11_layc_dvc)
  (setvar "celtype" "bylayer")
  (setq lind_pt2 pt1
	line_pt2 pt2
  )
  (if (= scd11_var_lind "1")
    (command "._line" "_non" lind_pt1 "_non" lind_pt2 "")
  )
  (if (= scd11_var_line "1")
    (command "._line" "_non" line_pt1 "_non" line_pt2 "")
  )
  (devolve)
  (prompt "\nDitite <UB> para retornar...")
  (princ)
)

;ao escolher um radio_button
(defun scd11_radio ()
  (setq scd11_var_svis $value)
  (scd11_upslide)
)

;atualização do Slide pelo radio_button escolhido
(defun scd11_upslide ()
  (cond
    ((= scd11_var_svis "scd11_vis_01")
     (setq scd11_type 1)
     (setq x (dimx_tile "scd_11_slide")
	   y (dimy_tile "scd_11_slide"))
     (start_image "scd_11_slide")
     (fill_image 0 0 x y -2)
     (slide_image 0 0 x y (strcat cnp_root "/slides/scd_11.sld"))
     (end_image)
    )
    ((= scd11_var_svis "scd11_vis_02")
     (setq scd11_type 2)
     (setq x (dimx_tile "scd_11_slide")
	   y (dimy_tile "scd_11_slide"))
     (start_image "scd_11_slide")
     (fill_image 0 0 x y -2)
     (slide_image 0 0 x y (strcat cnp_root "/slides/scd_12.sld"))
     (end_image)
    )
    ((= scd11_var_svis "scd11_vis_03")
     (setq scd11_type 3)
     (setq x (dimx_tile "scd_11_slide")
	   y (dimy_tile "scd_11_slide"))
     (start_image "scd_11_slide")
     (fill_image 0 0 x y -2)
     (slide_image 0 0 x y (strcat cnp_root "/slides/scd_13.sld"))
     (end_image)
    )
  )
)   

;***********************************
;Configuração de Cores e Layers     
;***********************************
(defun scd11_laycol_button ()
  (scd11_last_writefile)
  (scd11_layc_file)
  (setq dcl_id (load_dialog (strcat cnp_root "/lisp/cadnorma.dcl")))
  (if (not (new_dialog "scd11_cfglayc" dcl_id)) (exit))
  ;degraus em vista
  (set_tile "scd11_layc_dvl" scd11_layc_dvl)
  (action_tile "scd11_layc_dvl" "(setq scd11_layc_dvl $value)")
  (start_image "scd11_layc_dvc")
  (fill_image  0  0
    (dimx_tile "scd11_layc_dvc")
    (dimy_tile "scd11_layc_dvc")
    (fix (distof scd11_layc_dvc))
  )
  (end_image)
  (action_tile "scd11_layc_dvc" "(scd11_layc_dvc_color)")
  ;degraus em projeção
  (set_tile "scd11_layc_dpl" scd11_layc_dpl)
  (action_tile "scd11_layc_dpl" "(setq scd11_layc_dpl $value)")
  (start_image "scd11_layc_dpc")
  (fill_image  0  0
    (dimx_tile "scd11_layc_dpc")
    (dimy_tile "scd11_layc_dpc")
    (fix (distof scd11_layc_dpc))
  )
  (end_image)
  (action_tile "scd11_layc_dpc" "(scd11_layc_dpc_color)")
  ;Corrimão
  (set_tile "scd11_layc_crl" scd11_layc_crl)
  (action_tile "scd11_layc_crl" "(setq scd11_layc_crl $value)")
  (start_image "scd11_layc_crc")
  (fill_image  0  0
    (dimx_tile "scd11_layc_crc")
    (dimy_tile "scd11_layc_crc")
    (fix (distof scd11_layc_crc))
  )
  (end_image)
  (action_tile "scd11_layc_crc" "(scd11_layc_crc_color)")
  ;Interrupção
  (set_tile "scd11_layc_itl" scd11_layc_itl)
  (action_tile "scd11_layc_itl" "(setq scd11_layc_itl $value)")
  (start_image "scd11_layc_itc")
  (fill_image  0  0
    (dimx_tile "scd11_layc_itc")
    (dimy_tile "scd11_layc_itc")
    (fix (distof scd11_layc_itc))
  )
  (end_image)
  (action_tile "scd11_layc_itc" "(scd11_layc_itc_color)")
  ;ok_cancel
  (action_tile "cancel" "(done_dialog 0)")
  (action_tile "accept" "(done_dialog 1)")
  ;start_dialog
  (setq scd11_layc_id (start_dialog))
  (unload_dialog dcl_id)
  (if (= scd11_layc_id 1)
    (progn
      (scd11_layc_writefile)
      (scd11_main)
    )
  )
  (if (= scd11_layc_id 0) (scd11_main))
)

;escolher cor dos degraus em vista
(defun scd11_layc_dvc_color ()
  (setq scd11_layc_dvc_newcol (acad_colordlg (fix (distof scd11_layc_dvc))))
  (if (/= nil scd11_layc_dvc_newcol) (setq scd11_layc_dvc (rtos scd11_layc_dvc_newcol 2 0)))
  (start_image "scd11_layc_dvc")
  (fill_image  0  0
    (dimx_tile "scd11_layc_dvc")
    (dimy_tile "scd11_layc_dvc")
    (fix (distof scd11_layc_dvc))
  )
  (end_image)
)


;escolher cor dos degraus em projeção
(defun scd11_layc_dpc_color ()
  (setq scd11_layc_dpc_newcol (acad_colordlg (fix (distof scd11_layc_dpc))))
  (if (/= nil scd11_layc_dpc_newcol) (setq scd11_layc_dpc (rtos scd11_layc_dpc_newcol 2 0)))
  (start_image "scd11_layc_dpc")
  (fill_image  0  0
    (dimx_tile "scd11_layc_dpc")
    (dimy_tile "scd11_layc_dpc")
    (fix (distof scd11_layc_dpc))
  )
  (end_image)
)

;escolher cor do corrimão
(defun scd11_layc_crc_color ()
  (setq scd11_layc_crc_newcol (acad_colordlg (fix (distof scd11_layc_crc))))
  (if (/= nil scd11_layc_crc_newcol) (setq scd11_layc_crc (rtos scd11_layc_crc_newcol 2 0)))
  (start_image "scd11_layc_crc")
  (fill_image  0  0
    (dimx_tile "scd11_layc_crc")
    (dimy_tile "scd11_layc_crc")
    (fix (distof scd11_layc_crc))
  )
  (end_image)
)


;escolher cor da linha de interrupção
(defun scd11_layc_itc_color ()
  (setq scd11_layc_itc_newcol (acad_colordlg (fix (distof scd11_layc_itc))))
  (if (/= nil scd11_layc_itc_newcol) (setq scd11_layc_itc (rtos scd11_layc_itc_newcol 2 0)))
  (start_image "scd11_layc_itc")
  (fill_image  0  0
    (dimx_tile "scd11_layc_itc")
    (dimy_tile "scd11_layc_itc")
    (fix (distof scd11_layc_itc))
  )
  (end_image)
)


;lê os dados iniciais da DCL no arquivo de dados
(defun scd11_layc_file ()
  (if (findfile (strcat cnp_root "/config/scd11_layc.txt"))
    (scd11_layc_readfile)
    (progn
      (setq file (open (strcat cnp_root "/config/scd11_layc.txt") "w" "utf8"))
      (write-line "Escada" file)
      (write-line "3" file)
      (write-line "Escada" file)
      (write-line "3" file)
      (write-line "Escada" file)
      (write-line "1" file)
      (write-line "Escada" file)
      (write-line "1" file)
      (close file)
      (scd11_layc_readfile)
    )
  )
)

;função que lê o arquivo de dados
(defun scd11_layc_readfile ()
  (setq	file (open (strcat cnp_root "/config/scd11_layc.txt") "r" "utf8"))
  (setq	scd11_layc_dvl (read-line file))
  (setq	scd11_layc_dvc (read-line file))
  (setq	scd11_layc_dpl (read-line file))
  (setq	scd11_layc_dpc (read-line file))
  (setq	scd11_layc_crl (read-line file))
  (setq	scd11_layc_crc (read-line file))
  (setq	scd11_layc_itl (read-line file))
  (setq	scd11_layc_itc (read-line file))
  (close file)
)

;função que escreve o arquivo de dados
(defun scd11_layc_writefile ()
  (setq	file (open (strcat cnp_root "/config/scd11_layc.txt") "w" "utf8"))
  (write-line scd11_layc_dvl file)
  (write-line scd11_layc_dvc file)
  (write-line scd11_layc_dpl file)
  (write-line scd11_layc_dpc file)
  (write-line scd11_layc_crl file)
  (write-line scd11_layc_crc file)
  (write-line scd11_layc_itl file)
  (write-line scd11_layc_itc file)
  (close file)
)


;clica em dois pontos = nova largura do degrau
(defun scd11_getldeg_button ()
  (scd11_last_writefile)
  (setq ldeg_dist nil
	pt1 (getpoint "\nPrimeiro ponto da ldegura... ")
	pt2 (getpoint pt1 "Segundo ponto da ldegura... ")
	ldeg_dist (distance pt1 pt2)
  )
  (cond
    ((= cn7_dwgunit 1.0) (setq new_dist (* ldeg_dist 100.0)))
    ((= cn7_dwgunit 100.0) (setq new_dist (* ldeg_dist 1.0)))
    ((= cn7_dwgunit 1000.0) (setq new_dist (* ldeg_dist 0.1)))
  )
  (if new_dist
    (progn
      (setq scd11_var_ldeg (rtos new_dist 2 2))
      (scd11_last_writefile)
    )
  )
  (scd11_main)
)

;clica em dois pontos = nova largura
(defun scd11_getlarg_button ()
  (scd11_last_writefile)
  (setq larg_dist nil
	pt1 (getpoint "\nPrimeiro ponto da largura... ")
	pt2 (getpoint pt1 "Segundo ponto da largura... ")
	larg_dist (distance pt1 pt2)
  )
  (cond
    ((= cn7_dwgunit 1.0) (setq new_dist (* larg_dist 100.0)))
    ((= cn7_dwgunit 100.0) (setq new_dist (* larg_dist 1.0)))
    ((= cn7_dwgunit 1000.0) (setq new_dist (* larg_dist 0.1)))
  )
  (if new_dist
    (progn
      (setq scd11_var_larg (rtos new_dist 2 2))
      (scd11_last_writefile)
    )
  )
  (scd11_main)
)
  
;verifica valor de entrada para largura do degrau
(defun scd11_getldeg_action ()
  (setq scd11_var_newldeg $value)
  (if (distof scd11_var_newldeg)
    (setq scd11_var_ldeg scd11_var_newldeg)
    (progn
      (alert "Valor Inválido!")
      (set_tile "scd11_getldeg" scd11_var_ldeg)
      (mode_tile "scd11_getldeg" 2)
    )
  )
)

;verifica valor de entrada para número de degraus
(defun scd11_getndeg_action ()
  (setq scd11_var_newndeg $value)
  (if (and (distof scd11_var_newndeg) (= (distof scd11_var_newndeg) (fix (distof scd11_var_newndeg))))
    (setq scd11_var_ndeg scd11_var_newndeg)
    (progn
      (alert "Valor Inválido!\nDigite um número inteiro.")
      (set_tile "scd11_getndeg" scd11_var_ndeg)
      (mode_tile "scd11_getndeg" 2)
    )
  )
)

;verifica valor de entrada para largura
(defun scd11_getlarg_action ()
  (setq scd11_var_newlarg $value)
  (if (distof scd11_var_newlarg)
    (setq scd11_var_larg scd11_var_newlarg)
    (progn
      (alert "Valor Inválido!")
      (set_tile "scd11_getlarg" scd11_var_larg)
      (mode_tile "scd11_getlarg" 2)
    )
  )
)

;lê os dados iniciais da DCL no arquivo de dados
(defun scd11_last_file ()
  (if (findfile (strcat cnp_root "/config/scd11_last.txt"))
    (scd11_last_readfile)
    (progn
      (setq file (open (strcat cnp_root "/config/scd11_last.txt") "w" "utf8"))
      (write-line "100" file)
      (write-line "5" file)
      (write-line "30" file)
      (write-line "1" file)
      (write-line "1" file)
      (write-line "1" file)
      (write-line "1" file)
      (write-line "scd11_vis_02" file)
      (close file)
      (scd11_last_readfile)
    )
  )
)

;função que lê o arquivo de dados
(defun scd11_last_readfile ()
  (setq	file (open (strcat cnp_root "/config/scd11_last.txt") "r" "utf8"))
  (setq	scd11_var_larg (read-line file))
  (setq	scd11_var_ndeg (read-line file))
  (setq	scd11_var_ldeg (read-line file))
  (setq	scd11_var_lind (read-line file))
  (setq	scd11_var_line (read-line file))
  (setq	scd11_var_cord (read-line file))
  (setq	scd11_var_core (read-line file))
  (setq	scd11_var_svis (read-line file))
  (close file)
)

;função que escreve o arquivo de dados
(defun scd11_last_writefile ()
  (setq	file (open (strcat cnp_root "/config/scd11_last.txt") "w" "utf8"))
  (write-line scd11_var_larg file)
  (write-line scd11_var_ndeg file)
  (write-line scd11_var_ldeg file)
  (write-line scd11_var_lind file)
  (write-line scd11_var_line file)
  (write-line scd11_var_cord file)
  (write-line scd11_var_core file)
  (write-line scd11_var_svis file)
  (close file)
)

;procedimento inicial para escadas
(defun scd11_start ()
  (cn7_init)
  (guarda '("blipmode" "cecolor" "celtype" "clayer" "cmdecho" "orthomode"
          "textstyle" "luprec" "osmode" ))
  (setvar "cecolor" "bylayer")
  (scd11_last_file)
  (scd11_layc_file)
  (cond
    ((= cn7_dwgunit 1) (setq scd11_fator 0.01 scd11_blkscl 1.0))
    ((= cn7_dwgunit 100) (setq scd11_fator 1.0 scd11_blkscl 100.0))
    ((= cn7_dwgunit 1000) (setq scd11_fator 10.0 scd11_blkscl 1000.0))
  )
)

(defun c:sc3 () (scd12_main))

(defun scd12_main ()
  (scd12_start)
  (setq dcl_id (load_dialog (strcat cnp_root "/lisp/cadnorma.dcl")))
  (if (not (new_dialog "scd12" dcl_id)) (exit))
  (set_tile "scd12_vis_radio" scd12_var_svis)
  (action_tile "scd12_vis_radio" "(scd12_radio)")
  ;slide
  (scd12_upslide)
  ;dados de  construção
  (set_tile "scd12_getdiae" scd12_var_diae)
  (action_tile "scd12_getdiae" "(scd12_getdiae_action)")
  (action_tile "scd12_pikdiae" "(done_dialog 2)")
  (set_tile "scd12_getdiai" scd12_var_diai)
  (action_tile "scd12_getdiai" "(scd12_getdiai_action)")
  (action_tile "scd12_pikdiai" "(done_dialog 3)")
;;;  ;toggles
  (set_tile "scd12_getcore" scd12_var_core)
  (action_tile "scd12_getcore" "(setq scd12_var_core $value)")
  (set_tile "scd12_getcori" scd12_var_cori)
  (action_tile "scd12_getcori" "(setq scd12_var_cori $value)")
;;;  ;cores e layers
  (action_tile "scd12_cfglayc" "(done_dialog 4)")
  ;comandos gerais
  (action_tile "cancel" "(done_dialog 0)")
  (action_tile "accept" "(done_dialog 1)")
  ;ativação da DCL
  (setq scd12_dcl_id (start_dialog))
  (unload_dialog dcl_id)
  ;ações dos botões
  (if (= 1 scd12_dcl_id) (scd12_ok_action))
  (if (= 2 scd12_dcl_id) (scd12_getdiae_button))
  (if (= 3 scd12_dcl_id) (scd12_getdiai_button))
  (if (= 4 scd12_dcl_id) (scd12_laycol_button))
)

;decide o tipo de escada que vai desenhar
(defun scd12_ok_action ()
  (scd12_last_writefile)
  (cond
    ((= scd12_var_svis "scd12_vis_01") (scd12_draw_01))
    ((= scd12_var_svis "scd12_vis_02") (scd12_draw_02))
    ((= scd12_var_svis "scd12_vis_03") (scd12_draw_03))
  )
)

;desenha escada em projeção
(defun scd12_draw_03 ()
  (command "._undo" "_m")
  (scd12_last_writefile)
  (setq scd12_pt0 (getpoint "\nClique no ponto central da escada... "))
  (setq scd12_pt1 (polar scd12_pt0 0 (* scd12_fator (/ (distof scd12_var_diai) 2)))
	scd12_pt2 (polar scd12_pt0 0 (* scd12_fator (/ (distof scd12_var_diae) 2)))
	scd12_pt3 (polar scd12_pt0 (/ (* 3 pi) 2) (* scd12_fator (/ (distof scd12_var_diae) 2)))
	scd12_pt4 (polar scd12_pt0 (/ (* 3 pi) 2) (* scd12_fator (/ (distof scd12_var_diai) 2)))
  )
  ;desenha os contornos
  (cn7_verylayer scd12_layc_dpl 7)
  (setvar "cecolor" scd12_layc_dpc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._circle" "_non" scd12_pt0 "_non" scd12_pt1)
  (command "._circle" "_non" scd12_pt0 "_non" scd12_pt2)
  (command "._line" "_non" scd12_pt4 "_non" scd12_pt3 "")
  (command "._array" (entlast) "" "_p" "_non" scd12_pt0 8 360 "_y")
  (devolve)
  (prompt "\nDitite <UB> para retornar...")
  (princ)
)

;desenha a escada subindo
(defun scd12_draw_02 ()
  (command "._undo" "_m")
  (scd12_last_writefile)
  (setq scd12_pt0 (getpoint "\nClique no ponto central da escada... "))
  (setq scd12_pt1 (polar scd12_pt0 0 (* scd12_fator (/ (distof scd12_var_diai) 2)))
	scd12_pt2 (polar scd12_pt0 0 (* scd12_fator (/ (distof scd12_var_diae) 2)))
	scd12_pt3 (polar scd12_pt0 (/ (* 3 pi) 2) (* scd12_fator (/ (distof scd12_var_diae) 2)))
	scd12_pt4 (polar scd12_pt3 0  (* scd12_fator (/ (distof scd12_var_diae) 2)))
	scd12_pt5 (polar scd12_pt0 (/ (* 3 pi) 2) (* scd12_fator (/ (distof scd12_var_diai) 2)))
	scd12_pt6 (polar scd12_pt5 0  (* scd12_fator (/ (distof scd12_var_diae) 2)))
	scd12_pt7 (polar scd12_pt0 (/ (* 5 pi) 4) (* scd12_fator (/ (distof scd12_var_diai) 2)))
	scd12_pt8 (polar scd12_pt0 (/ (* 5 pi) 4) (* scd12_fator (/ (distof scd12_var_diae) 2)))
	scd12_pt9 (polar scd12_pt0 pi (* scd12_fator (/ (distof scd12_var_diai) 2)))
	scd12_pt10 (polar scd12_pt0 pi (* scd12_fator (/ (distof scd12_var_diae) 2)))
	scd12_pt11 (polar scd12_pt0 (/ (* 3 pi) 4) (* scd12_fator (/ (distof scd12_var_diai) 2)))
	scd12_pt12 (polar scd12_pt0 (/ (* 3 pi) 4) (* scd12_fator (/ (distof scd12_var_diae) 2)))
	scd12_pt13 (polar scd12_pt0 (/ pi 2) (* scd12_fator (/ (distof scd12_var_diai) 2)))
	scd12_pt14 (polar scd12_pt0 (/ pi 2) (* scd12_fator (/ (distof scd12_var_diae) 2)))
	scd12_pt15 (polar scd12_pt0 (/ pi 4) (* scd12_fator (/ (distof scd12_var_diai) 2)))
	scd12_pt16 (polar scd12_pt0 (/ pi 4) (* scd12_fator (/ (distof scd12_var_diae) 2)))
	scd12_pt26 (polar scd12_pt5 (angle scd12_pt5 scd12_pt3) (/ (distance scd12_pt5 scd12_pt3) 2))
	scd12_pt27 (polar scd12_pt1 (angle scd12_pt1 scd12_pt2) (/ (distance scd12_pt1 scd12_pt2) 2))
  )
  ;desenha os contornos
  (cn7_verylayer scd12_layc_itl 7)
  (setvar "cecolor" scd12_layc_itc)
  (setvar "celtype" "bylayer")
  (command "._circle" "_non" scd12_pt0 "_non" scd12_pt1)
  (command "._arc" "_c" "_non" scd12_pt0 "_non" scd12_pt2 "_non" scd12_pt3)
  ;desenha os degraus em vista
  (cn7_verylayer scd12_layc_dvl 7)
  (setvar "cecolor" scd12_layc_dvc)
  (command "._line" "_non" scd12_pt5 "_non" scd12_pt3 "")
  (command "._line" "_non" scd12_pt7 "_non" scd12_pt8 "")
  (command "._line" "_non" scd12_pt9 "_non" scd12_pt10 "")
  (command "._line" "_non" scd12_pt11 "_non" scd12_pt12 "")
  ;desenha os degraus em projeção
  (cn7_verylayer scd12_layc_dpl 7)
  (setvar "cecolor" scd12_layc_dpc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._line" "_non" scd12_pt13 "_non" scd12_pt14 "")
  (command "._line" "_non" scd12_pt15 "_non" scd12_pt16 "")
  (command "._line" "_non" scd12_pt1 "_non" scd12_pt2 "")
  ;desenha o arco em projeção
  (command "._arc" "_c" "_non" scd12_pt0 "_non" scd12_pt3 "_non" scd12_pt2)
  ;desenha a seta de fluxo
  (cn7_verylayer scd12_layc_dvl 7)
  (setvar "cecolor" "1")
  (setvar "celtype" "bylayer")
  (command "._insert" (strcat cnp_root "/blocos/escada_sobe") "_scale" cn7_blkscl "_non" scd12_pt26 "0")
  (command "._explode" (entlast) "._chprop" "_p" "" "_la" scd12_layc_dvl "_c" "1" "")
  (command "._arc" "_c" "_non" scd12_pt0 "_non" scd12_pt27 "_non" scd12_pt26)
  (command "._insert" (strcat cnp_root "/blocos/util_st1") "_scale" cn7_blkscl "_non" scd12_pt27 "90")
  (command "._explode" (entlast) "._chprop" "_p" "" "_la" scd12_layc_dvl "_c" "1" "")
  ;desenha o corrimão externo
  (if (= scd12_var_core "1")
    (progn
      (setq scd12_pt17 (polar scd12_pt4 (/ pi 2) (* scd12_fator 5.0))
	    scd12_pt18 (polar scd12_pt3 (/ pi 2) (* scd12_fator 5.0))
	    scd12_pt19 (polar scd12_pt14 (/ (* 3 pi) 2) (* scd12_fator 5.0))
	    scd12_pt20 (polar scd12_pt2 pi (* scd12_fator 5.0))
      )
      (command "._arc" "_c" "_non" scd12_pt0 "_non" scd12_pt20 "_non" scd12_pt19)
      (cn7_verylayer scd12_layc_crl 7)
      (setvar "cecolor" scd12_layc_crc)
      (setvar "celtype" "bylayer")
      (command "._arc" "_c" "_non" scd12_pt0 "_non" scd12_pt19 "_non" scd12_pt18)
;;;      (command "._line" "_non" scd12_pt18 "_non" scd12_pt17 "")
    )
  )
  ;desenha o corrimão interno
  (if (= scd12_var_cori "1")
    (progn
      (setq scd12_pt21 (polar scd12_pt6 (* 3 (/ pi 2)) (* scd12_fator 5.0))
	    scd12_pt22 (polar scd12_pt5 (* 3 (/ pi 2)) (* scd12_fator 5.0))
	    scd12_pt23 (polar scd12_pt13 (/ pi 2) (* scd12_fator 5.0))
	    scd12_pt24 (polar scd12_pt1 0 (* scd12_fator 5.0))
      )
      (cn7_verylayer scd12_layc_dpl 7)
      (setvar "cecolor" scd12_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
      (command "._arc" "_c" "_non" scd12_pt0 "_non" scd12_pt24 "_non" scd12_pt23)
      (cn7_verylayer scd12_layc_crl 7)
      (setvar "cecolor" scd12_layc_crc)
      (setvar "celtype" "bylayer")
      (command "._arc" "_c" "_non" scd12_pt0 "_non" scd12_pt23 "_non" scd12_pt22)
;;;      (command "._line" "_non" scd12_pt22 "_non" scd12_pt21 "")
    )
  )
  (devolve)
  (prompt "\nDitite <UB> para retornar...")
  (princ)
)

;desenha a escada descendo
(defun scd12_draw_01 ()
  (command "._undo" "_m")
  (scd12_last_writefile)
  (setq scd12_pt0 (getpoint "\nClique no ponto central da escada... "))
  (setq scd12_pt1 (polar scd12_pt0 0 (* scd12_fator (/ (distof scd12_var_diai) 2)))
	scd12_pt2 (polar scd12_pt0 0 (* scd12_fator (/ (distof scd12_var_diae) 2)))
	scd12_pt3 (polar scd12_pt0 (/ (* 3 pi) 2) (* scd12_fator (/ (distof scd12_var_diae) 2)))
	scd12_pt4 (polar scd12_pt3 0  (* scd12_fator (/ (distof scd12_var_diae) 2)))
	scd12_pt5 (polar scd12_pt0 (/ (* 3 pi) 2) (* scd12_fator (/ (distof scd12_var_diai) 2)))
	scd12_pt6 (polar scd12_pt5 0  (* scd12_fator (/ (distof scd12_var_diae) 2)))
	scd12_pt7 (polar scd12_pt0 (/ (* 5 pi) 4) (* scd12_fator (/ (distof scd12_var_diai) 2)))
	scd12_pt8 (polar scd12_pt0 (/ (* 5 pi) 4) (* scd12_fator (/ (distof scd12_var_diae) 2)))
	scd12_pt9 (polar scd12_pt0 pi (* scd12_fator (/ (distof scd12_var_diai) 2)))
	scd12_pt10 (polar scd12_pt0 pi (* scd12_fator (/ (distof scd12_var_diae) 2)))
	scd12_pt11 (polar scd12_pt0 (/ (* 3 pi) 4) (* scd12_fator (/ (distof scd12_var_diai) 2)))
	scd12_pt12 (polar scd12_pt0 (/ (* 3 pi) 4) (* scd12_fator (/ (distof scd12_var_diae) 2)))
	scd12_pt13 (polar scd12_pt0 (/ pi 2) (* scd12_fator (/ (distof scd12_var_diai) 2)))
	scd12_pt14 (polar scd12_pt0 (/ pi 2) (* scd12_fator (/ (distof scd12_var_diae) 2)))
	scd12_pt15 (polar scd12_pt0 (/ pi 4) (* scd12_fator (/ (distof scd12_var_diai) 2)))
	scd12_pt16 (polar scd12_pt0 (/ pi 4) (* scd12_fator (/ (distof scd12_var_diae) 2)))
	scd12_pt25 (polar scd12_pt6 (angle scd12_pt6 scd12_pt4) (/ (distance scd12_pt6 scd12_pt4) 2))
	scd12_pt26 (polar scd12_pt5 (angle scd12_pt5 scd12_pt3) (/ (distance scd12_pt5 scd12_pt3) 2))
	scd12_pt27 (polar scd12_pt13 (angle scd12_pt13 scd12_pt14) (/ (distance scd12_pt13 scd12_pt14) 2))
  )
  (setq x (sqrt (- (expt (/ (* (distof scd12_var_diae) scd12_fator) 2) 2)
		   (expt (/ (* (distof scd12_var_diai) scd12_fator) 2) 2)))
	scd12_ptx (polar scd12_pt5 0 x)
  )
  ;desenha os contornos
  (cn7_verylayer scd12_layc_itl 7)
  (setvar "cecolor" scd12_layc_itc)
  (setvar "celtype" "bylayer")
  (command "._circle" "_non" scd12_pt0 "_non" scd12_pt1)
  (command "._arc" "_c" "_non" scd12_pt0 "_non" scd12_ptx "_non" scd12_pt3)
  (command "._line" "_non" scd12_pt3 "_non" scd12_pt4 "_non" scd12_pt6 "_non" scd12_pt5 "")
  ;desenha os degraus em vista
  (cn7_verylayer scd12_layc_dvl 7)
  (setvar "cecolor" scd12_layc_dvc)
  (command "._line" "_non" scd12_pt5 "_non" scd12_pt3 "")
  (command "._line" "_non" scd12_pt7 "_non" scd12_pt8 "")
  (command "._line" "_non" scd12_pt9 "_non" scd12_pt10 "")
  (command "._line" "_non" scd12_pt11 "_non" scd12_pt12 "")
  ;desenha os degraus em projeção
  (cn7_verylayer scd12_layc_dpl 7)
  (setvar "cecolor" scd12_layc_dpc)
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._line" "_non" scd12_pt13 "_non" scd12_pt14 "")
  (command "._line" "_non" scd12_pt15 "_non" scd12_pt16 "")
  (command "._line" "_non" scd12_pt1 "_non" scd12_pt2 "")
  ;desenha o arco em projeção
  (command "._arc" "_c" "_non" scd12_pt0 "_non" scd12_pt3 "_non" scd12_ptx)
  ;desenha a seta de fluxo
  (cn7_verylayer scd12_layc_dvl 7)
  (setvar "cecolor" "1")
  (setvar "celtype" "bylayer")
  (command "._insert" (strcat cnp_root "/blocos/escada_sobe") "_scale" cn7_blkscl "_non" scd12_pt25 "0")
  (command "._explode" (entlast) "._chprop" "_p" "" "_la" scd12_layc_dvl "_c" "1" "")
  (command "._line" "_non" scd12_pt25 "_non" scd12_pt26 "")
  (command "._arc" "_c" "_non" scd12_pt0 "_non" scd12_pt27 "_non" scd12_pt26)
  (command "._insert" (strcat cnp_root "/blocos/util_st1") "_scale" cn7_blkscl "_non" scd12_pt27 "180")
  (command "._explode" (entlast) "._chprop" "_p" "" "_la" scd12_layc_dvl "_c" "1" "")
  ;desenha o corrimão externo
  (if (= scd12_var_core "1")
    (progn
      (setq scd12_pt17 (polar scd12_pt4 (/ pi 2) (* scd12_fator 5.0))
	    scd12_pt18 (polar scd12_pt3 (/ pi 2) (* scd12_fator 5.0))
	    scd12_pt19 (polar scd12_pt14 (/ (* 3 pi) 2) (* scd12_fator 5.0))
	    scd12_pt20 (polar scd12_pt2 pi (* scd12_fator 5.0))
      )
      (command "._arc" "_c" "_non" scd12_pt0 "_non" scd12_pt20 "_non" scd12_pt19)
      (cn7_verylayer scd12_layc_crl 7)
      (setvar "cecolor" scd12_layc_crc)
      (setvar "celtype" "bylayer")
      (command "._arc" "_c" "_non" scd12_pt0 "_non" scd12_pt19 "_non" scd12_pt18)
      (command "._line" "_non" scd12_pt18 "_non" scd12_pt17 "")
    )
  )
  ;desenha o corrimão interno
  (if (= scd12_var_cori "1")
    (progn
      (setq scd12_pt21 (polar scd12_pt6 (* 3 (/ pi 2)) (* scd12_fator 5.0))
	    scd12_pt22 (polar scd12_pt5 (* 3 (/ pi 2)) (* scd12_fator 5.0))
	    scd12_pt23 (polar scd12_pt13 (/ pi 2) (* scd12_fator 5.0))
	    scd12_pt24 (polar scd12_pt1 0 (* scd12_fator 5.0))
      )
      (cn7_verylayer scd12_layc_dpl 7)
      (setvar "cecolor" scd12_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
      (command "._arc" "_c" "_non" scd12_pt0 "_non" scd12_pt24 "_non" scd12_pt23)
      (cn7_verylayer scd12_layc_crl 7)
      (setvar "cecolor" scd12_layc_crc)
      (setvar "celtype" "bylayer")
      (command "._arc" "_c" "_non" scd12_pt0 "_non" scd12_pt23 "_non" scd12_pt22)
      (command "._line" "_non" scd12_pt22 "_non" scd12_pt21 "")
    )
  )
  (devolve)
  (prompt "\nDitite <UB> para retornar...")
  (princ)
)

;ao escolher um radio_button
(defun scd12_radio ()
  (setq scd12_var_svis $value)
  (scd12_upslide)
)

;atualização do Slide pelo radio_button escolhido
(defun scd12_upslide ()
  (cond
    ((= scd12_var_svis "scd12_vis_01")
     (setq scd12_type 1)
     (setq x (dimx_tile "scd_12_slide")
	   y (dimy_tile "scd_12_slide"))
     (start_image "scd_12_slide")
     (fill_image 0 0 x y -2)
     (slide_image 0 0 x y (strcat cnp_root "/slides/scd2_11.sld"))
     (end_image)
    )
    ((= scd12_var_svis "scd12_vis_02")
     (setq scd12_type 2)
     (setq x (dimx_tile "scd_12_slide")
	   y (dimy_tile "scd_12_slide"))
     (start_image "scd_12_slide")
     (fill_image 0 0 x y -2)
     (slide_image 0 0 x y (strcat cnp_root "/slides/scd2_12.sld"))
     (end_image)
    )
    ((= scd12_var_svis "scd12_vis_03")
     (setq scd12_type 3)
     (setq x (dimx_tile "scd_12_slide")
	   y (dimy_tile "scd_12_slide"))
     (start_image "scd_12_slide")
     (fill_image 0 0 x y -2)
     (slide_image 0 0 x y (strcat cnp_root "/slides/scd2_13.sld"))
     (end_image)
    )
  )
)   

;***********************************
;Configuração de Cores e Layers     
;***********************************
(defun scd12_laycol_button ()
  (scd12_last_writefile)
  (scd12_layc_file)
  (setq dcl_id (load_dialog (strcat cnp_root "/lisp/cadnorma.dcl")))
  (if (not (new_dialog "scd12_cfglayc" dcl_id)) (exit))
  ;degraus em vista
  (set_tile "scd12_layc_dvl" scd12_layc_dvl)
  (action_tile "scd12_layc_dvl" "(setq scd12_layc_dvl $value)")
  (start_image "scd12_layc_dvc")
  (fill_image  0  0
    (dimx_tile "scd12_layc_dvc")
    (dimy_tile "scd12_layc_dvc")
    (fix (distof scd12_layc_dvc))
  )
  (end_image)
  (action_tile "scd12_layc_dvc" "(scd12_layc_dvc_color)")
  ;degraus em projeção
  (set_tile "scd12_layc_dpl" scd12_layc_dpl)
  (action_tile "scd12_layc_dpl" "(setq scd12_layc_dpl $value)")
  (start_image "scd12_layc_dpc")
  (fill_image  0  0
    (dimx_tile "scd12_layc_dpc")
    (dimy_tile "scd12_layc_dpc")
    (fix (distof scd12_layc_dpc))
  )
  (end_image)
  (action_tile "scd12_layc_dpc" "(scd12_layc_dpc_color)")
  ;Corrimão
  (set_tile "scd12_layc_crl" scd12_layc_crl)
  (action_tile "scd12_layc_crl" "(setq scd12_layc_crl $value)")
  (start_image "scd12_layc_crc")
  (fill_image  0  0
    (dimx_tile "scd12_layc_crc")
    (dimy_tile "scd12_layc_crc")
    (fix (distof scd12_layc_crc))
  )
  (end_image)
  (action_tile "scd12_layc_crc" "(scd12_layc_crc_color)")
  ;Interrupção
  (set_tile "scd12_layc_itl" scd12_layc_itl)
  (action_tile "scd12_layc_itl" "(setq scd12_layc_itl $value)")
  (start_image "scd12_layc_itc")
  (fill_image  0  0
    (dimx_tile "scd12_layc_itc")
    (dimy_tile "scd12_layc_itc")
    (fix (distof scd12_layc_itc))
  )
  (end_image)
  (action_tile "scd12_layc_itc" "(scd12_layc_itc_color)")
  ;ok_cancel
  (action_tile "cancel" "(done_dialog 0)")
  (action_tile "accept" "(done_dialog 1)")
  ;start_dialog
  (setq scd12_layc_id (start_dialog))
  (unload_dialog dcl_id)
  (if (= scd12_layc_id 1)
    (progn
      (scd12_layc_writefile)
      (scd12_main)
    )
  )
  (if (= scd12_layc_id 0) (scd12_main))
)

;escolher cor dos degraus em vista
(defun scd12_layc_dvc_color ()
  (setq scd12_layc_dvc_newcol (acad_colordlg (fix (distof scd12_layc_dvc))))
  (if (/= nil scd12_layc_dvc_newcol) (setq scd12_layc_dvc (rtos scd12_layc_dvc_newcol 2 0)))
  (start_image "scd12_layc_dvc")
  (fill_image  0  0
    (dimx_tile "scd12_layc_dvc")
    (dimy_tile "scd12_layc_dvc")
    (fix (distof scd12_layc_dvc))
  )
  (end_image)
)


;escolher cor dos degraus em projeção
(defun scd12_layc_dpc_color ()
  (setq scd12_layc_dpc_newcol (acad_colordlg (fix (distof scd12_layc_dpc))))
  (if (/= nil scd12_layc_dpc_newcol) (setq scd12_layc_dpc (rtos scd12_layc_dpc_newcol 2 0)))
  (start_image "scd12_layc_dpc")
  (fill_image  0  0
    (dimx_tile "scd12_layc_dpc")
    (dimy_tile "scd12_layc_dpc")
    (fix (distof scd12_layc_dpc))
  )
  (end_image)
)

;escolher cor do corrimão
(defun scd12_layc_crc_color ()
  (setq scd12_layc_crc_newcol (acad_colordlg (fix (distof scd12_layc_crc))))
  (if (/= nil scd12_layc_crc_newcol) (setq scd12_layc_crc (rtos scd12_layc_crc_newcol 2 0)))
  (start_image "scd12_layc_crc")
  (fill_image  0  0
    (dimx_tile "scd12_layc_crc")
    (dimy_tile "scd12_layc_crc")
    (fix (distof scd12_layc_crc))
  )
  (end_image)
)


;escolher cor da linha de interrupção
(defun scd12_layc_itc_color ()
  (setq scd12_layc_itc_newcol (acad_colordlg (fix (distof scd12_layc_itc))))
  (if (/= nil scd12_layc_itc_newcol) (setq scd12_layc_itc (rtos scd12_layc_itc_newcol 2 0)))
  (start_image "scd12_layc_itc")
  (fill_image  0  0
    (dimx_tile "scd12_layc_itc")
    (dimy_tile "scd12_layc_itc")
    (fix (distof scd12_layc_itc))
  )
  (end_image)
)


;lê os dados iniciais da DCL no arquivo de dados
(defun scd12_layc_file ()
  (if (findfile (strcat cnp_root "/config/scd12_layc.txt"))
    (scd12_layc_readfile)
    (progn
      (setq file (open (strcat cnp_root "/config/scd12_layc.txt") "w" "utf8"))
      (write-line "Escada" file)
      (write-line "3" file)
      (write-line "Escada" file)
      (write-line "3" file)
      (write-line "Escada" file)
      (write-line "1" file)
      (write-line "Escada" file)
      (write-line "1" file)
      (close file)
      (scd12_layc_readfile)
    )
  )
)

;função que lê o arquivo de dados
(defun scd12_layc_readfile ()
  (setq	file (open (strcat cnp_root "/config/scd12_layc.txt") "r" "utf8"))
  (setq	scd12_layc_dvl (read-line file))
  (setq	scd12_layc_dvc (read-line file))
  (setq	scd12_layc_dpl (read-line file))
  (setq	scd12_layc_dpc (read-line file))
  (setq	scd12_layc_crl (read-line file))
  (setq	scd12_layc_crc (read-line file))
  (setq	scd12_layc_itl (read-line file))
  (setq	scd12_layc_itc (read-line file))
  (close file)
)

;função que escreve o arquivo de dados
(defun scd12_layc_writefile ()
  (setq	file (open (strcat cnp_root "/config/scd12_layc.txt") "w" "utf8"))
  (write-line scd12_layc_dvl file)
  (write-line scd12_layc_dvc file)
  (write-line scd12_layc_dpl file)
  (write-line scd12_layc_dpc file)
  (write-line scd12_layc_crl file)
  (write-line scd12_layc_crc file)
  (write-line scd12_layc_itl file)
  (write-line scd12_layc_itc file)
  (close file)
)

;clica em dois pontos = nova largura do degrau
(defun scd12_getdiai_button ()
  (scd12_last_writefile)
  (setq diai_dist nil
	pt1 (getpoint "\nPrimeiro ponto da diaiura... ")
	pt2 (getpoint pt1 "Segundo ponto da diaiura... ")
	diai_dist (distance pt1 pt2)
  )
  (cond
    ((= cn7_dwgunit 1.0) (setq new_dist (* diai_dist 100.0)))
    ((= cn7_dwgunit 100.0) (setq new_dist (* diai_dist 1.0)))
    ((= cn7_dwgunit 1000.0) (setq new_dist (* diai_dist 0.1)))
  )
  (if new_dist
    (progn
      (setq scd12_var_diai (rtos new_dist 2 2))
      (scd12_last_writefile)
    )
  )
  (scd12_main)
)

;clica em dois pontos = novo diâmetro externo
(defun scd12_getdiae_button ()
  (scd12_last_writefile)
  (setq diae_dist nil
	pt1 (getpoint "\nPrimeiro ponto da diaeura... ")
	pt2 (getpoint pt1 "Segundo ponto da diaeura... ")
	diae_dist (distance pt1 pt2)
  )
  (cond
    ((= cn7_dwgunit 1.0) (setq new_dist (* diae_dist 100.0)))
    ((= cn7_dwgunit 100.0) (setq new_dist (* diae_dist 1.0)))
    ((= cn7_dwgunit 1000.0) (setq new_dist (* diae_dist 0.1)))
  )
  (if new_dist
    (progn
      (setq scd12_var_diae (rtos new_dist 2 2))
      (scd12_last_writefile)
    )
  )
  (scd12_main)
)
  
;verifica valor de entrada para largura do degrau
(defun scd12_getdiai_action ()
  (setq scd12_var_newdiai $value)
  (if (distof scd12_var_newdiai)
    (setq scd12_var_diai scd12_var_newdiai)
    (progn
      (alert "Valor Inválido!")
      (set_tile "scd12_getdiai" scd12_var_diai)
      (mode_tile "scd12_getdiai" 2)
    )
  )
)

;verifica valor de entrada para diâmetro externo
(defun scd12_getdiae_action ()
  (setq scd12_var_newdiae $value)
  (if (distof scd12_var_newdiae)
    (setq scd12_var_diae scd12_var_newdiae)
    (progn
      (alert "Valor Inválido!")
      (set_tile "scd12_getdiae" scd12_var_diae)
      (mode_tile "scd12_getdiae" 2)
    )
  )
)

;lê os dados iniciais da DCL no arquivo de dados
(defun scd12_last_file ()
  (if (findfile (strcat cnp_root "/config/scd12_last.txt"))
    (scd12_last_readfile)
    (progn
      (setq file (open (strcat cnp_root "/config/scd12_last.txt") "w" "utf8"))
      (write-line "100" file)
      (write-line "10" file)
      (write-line "1" file)
      (write-line "1" file)
      (write-line "scd12_vis_02" file)
      (close file)
      (scd12_last_readfile)
    )
  )
)

;função que lê o arquivo de dados
(defun scd12_last_readfile ()
  (setq	file (open (strcat cnp_root "/config/scd12_last.txt") "r" "utf8"))
  (setq	scd12_var_diae (read-line file))
  (setq	scd12_var_diai (read-line file))
  (setq	scd12_var_core (read-line file))
  (setq	scd12_var_cori (read-line file))
  (setq	scd12_var_svis (read-line file))
  (close file)
)

;função que escreve o arquivo de dados
(defun scd12_last_writefile ()
  (setq	file (open (strcat cnp_root "/config/scd12_last.txt") "w" "utf8"))
  (write-line scd12_var_diae file)
  (write-line scd12_var_diai file)
  (write-line scd12_var_core file)
  (write-line scd12_var_cori file)
  (write-line scd12_var_svis file)
  (close file)
)

;procedimento inicial para escadas
(defun scd12_start ()
  (cn7_init)
  (guarda '("blipmode" "cecolor" "celtype" "clayer" "cmdecho" "orthomode"
          "textstyle" "luprec" "osmode" ))
  (setvar "cecolor" "bylayer")
  (scd12_last_file)
  (scd12_layc_file)
  (setq grp_type "2")
  (cn7_find_blkscl)
  (cond
    ((= cn7_dwgunit 1) (setq scd12_fator 0.01 scd12_blkscl 1.0))
    ((= cn7_dwgunit 100) (setq scd12_fator 1.0 scd12_blkscl 100.0))
    ((= cn7_dwgunit 1000) (setq scd12_fator 10.0 scd12_blkscl 1000.0))
  )
)

;protótipo: desenho de escada simples
(defun c:sc2 () (scd13_main))

(defun scd13_main ()
  (scd13_start)
  (setq dcl_id (load_dialog (strcat cnp_root "/lisp/cadnorma.dcl")))
  (if (not (new_dialog "scd13" dcl_id)) (exit))
  (set_tile "scd13_vis_radio" scd13_var_svis)
  (action_tile "scd13_vis_radio" "(scd13_radio)")
;;;  ;slide
  (scd13_upslide)
  ;largura dos degraus
  (set_tile "scd13_getldeg" scd13_var_ldeg)
  (action_tile "scd13_getldeg" "(scd13_getldeg_action)")
  (action_tile "scd13_pikldeg" "(done_dialog 2)")
  ;altura dos degraus
  (set_tile "scd13_gethdeg" scd13_var_hdeg)
  (action_tile "scd13_gethdeg" "(scd13_gethdeg_action)")
  (action_tile "scd13_pikhdeg" "(done_dialog 3)")
  ;quantidade de degraus
  (set_tile "scd13_getndeg" scd13_var_ndeg)
  (action_tile "scd13_getndeg" "(scd13_getndeg_action)")
  ;espessura da laje
  (set_tile "scd13_getllaj" scd13_var_llaj)
  (action_tile "scd13_getllaj" "(scd13_getllaj_action)")
  (action_tile "scd13_pikllaj" "(done_dialog 4)")
  ;corrimão
  (set_tile "scd13_tog_core" scd13_var_dcor)
  (set_tile "scd13_gethcor" scd13_var_hcor)
  (if (= "0" scd13_var_dcor) (mode_tile "scd13_gethcor" 1))
  (action_tile "scd13_tog_core" "(scd13_togcore_action)")
  (action_tile "scd13_gethcor" "(scd13_gethcor_action)")
  (action_tile "scd13_pikhcor" "(done_dialog 5)")
  ;cores e layers
  (action_tile "scd13_cfglayc" "(done_dialog 6)")
  ;comandos gerais
  (action_tile "cancel" "(done_dialog 0)")
  (action_tile "accept" "(done_dialog 1)")
  ;ativação da DCL
  (setq scd13_dcl_id (start_dialog))
  (unload_dialog dcl_id)
  ;ações dos botões
  (if (= 1 scd13_dcl_id) (scd13_ok_action))
  (if (= 2 scd13_dcl_id) (scd13_getldeg_button))
  (if (= 3 scd13_dcl_id) (scd13_gethdeg_button))
  (if (= 4 scd13_dcl_id) (scd13_getllaj_button))
  (if (= 5 scd13_dcl_id) (scd13_gethcor_button))
  (if (= 6 scd13_dcl_id) (scd13_laycol_button))

)

;decide o tipo de escada que vai desenhar
(defun scd13_ok_action ()
  (scd13_last_writefile)
  (scd13_draw_01)
;;;  (cond
;;;    ((= scd13_var_svis "scd13_vis_01") (scd13_draw_01))
;;;    ((= scd13_var_svis "scd13_vis_02") (scd13_draw_02))
;;;  )
)

;ao clicar no toggle de corrimão
(defun scd13_togcore_action ()
  (setq scd13_var_dcor $value)
  (if (= "0" scd13_var_dcor)
    (mode_tile "scd13_gethcor" 1)
    (progn
      (mode_tile "scd13_gethcor" 0)
      (mode_tile "scd13_gethcor" 2)
    )
  )
)

;desenha a escada descendo
(defun scd13_draw_01 ()
  (command "._undo" "_m")
  (scd13_last_writefile)
  (setvar "orthomode" 1)
  (setq scd13_pt0 (getpoint "\nClique no ponto inicial da escada... ")
	scd13_dir (getangle scd13_pt0 "\nLado para desenhar...")
  )
  ;calcula o deslocamento do ponto na laje
  (setq hip (sqrt (+ (expt (* scd13_fator (distof scd13_var_ldeg)) 2)
		     (expt (* scd13_fator (distof scd13_var_hdeg)) 2)))
	dx (/ (* scd13_fator (distof scd13_var_llaj) hip)
	      (* scd13_fator (distof scd13_var_hdeg))
	  )
  )
  ;desenha o primeiro degrau
  (setq scd13_pt1 scd13_pt0
	scd13_pt2 (polar scd13_pt1 (/ pi 2) (* scd13_fator (distof scd13_var_hdeg)))
	scd13_pt3 (polar scd13_pt2 scd13_dir (* scd13_fator (distof scd13_var_ldeg)))
	scd13_pc1 (polar scd13_pt2 scd13_dir (* scd13_fator 5.0))
	scd13_pl1 (polar scd13_pt1 scd13_dir dx)
  )
  ;atualiza o layer,para vista e projeção
  (if (= "scd13_vis_01" scd13_var_svis)
    (progn
      (cn7_verylayer scd13_layc_dvl 7)
      (setvar "cecolor" scd13_layc_dvc)
      (setvar "celtype" "bylayer")
    )
    (progn
      (cn7_verylayer scd13_layc_dpl 7)
      (setvar "cecolor" scd13_layc_dpc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
    )
  )
  (command "._line" "_non" scd13_pt1 "_non" scd13_pt2 "_non" scd13_pt3 "")
  (repeat (- (fix (distof scd13_var_ndeg)) 2)
    (setq scd13_pt1 scd13_pt3
	  scd13_pt2 (polar scd13_pt1 (/ pi 2) (* scd13_fator (distof scd13_var_hdeg)))
	  scd13_pt3 (polar scd13_pt2 scd13_dir (* scd13_fator (distof scd13_var_ldeg)))
    )
    (command "._line" "_non" scd13_pt1 "_non" scd13_pt2 "_non" scd13_pt3 "")
  )
  (setq scd13_pt1 scd13_pt3
	scd13_pt2 (polar scd13_pt1 (/ pi 2) (* scd13_fator (distof scd13_var_hdeg)))
	scd13_pt3 (polar scd13_pt2 scd13_dir (* scd13_fator (distof scd13_var_ldeg)))
  )
  (command "._line" "_non" scd13_pt1 "_non" scd13_pt2 "")
  (setq scd13_pl2 (polar scd13_pt1 scd13_dir dx))
  (command "._line" "_non" scd13_pl1 "_non" scd13_pl2 "")
  ;desenha o corrimão
  (if (= scd13_var_dcor "1")
    (progn
      (setq scd13_pc2 (polar scd13_pt2 scd13_dir (* scd13_fator 5.0))
	    scd13_pc3 (polar scd13_pc1 (/ pi 2) (* scd13_fator (distof scd13_var_hcor)))
	    scd13_pc4 (polar scd13_pc2 (/ pi 2) (* scd13_fator (distof scd13_var_hcor)))
      )
      (if (= "scd13_vis_01" scd13_var_svis)
        (progn
          (cn7_verylayer scd13_layc_crl 7)
          (setvar "cecolor" scd13_layc_crc)
          (setvar "celtype" "bylayer")
        )
        (progn
          (cn7_verylayer scd13_layc_dpl 7)
          (setvar "cecolor" scd13_layc_dpc)
          (if (not (tblsearch "ltype" "hidden2"))
	    (command "._linetype" "_l" "hidden2" (strcat cnp_root "/modelos/cadnorma.lin") "")
	    (command "._linetype" "_l" "hidden2" (strcat cnp_root "/modelos/cadnorma.lin") "_y" "")
          )
          (setvar "celtype" "hidden2")
        )
      )
      (command "._line" "_non" scd13_pc1 "_non" scd13_pc3 "_non" scd13_pc4 "_non" scd13_pc2 "")
    )
  )
  (devolve)
  (prompt "\nDitite <UB> para retornar...")
  (princ)
)

;ao escolher um radio_button
(defun scd13_radio ()
  (setq scd13_var_svis $value)
  (scd13_upslide)
)

;atualização do Slide pelo radio_button escolhido
(defun scd13_upslide ()
  (cond
    ((= scd13_var_svis "scd13_vis_01")
     (setq scd13_type 1)
     (setq x (dimx_tile "scd_13_slide")
	   y (dimy_tile "scd_13_slide"))
     (start_image "scd_13_slide")
     (fill_image 0 0 x y -2)
     (slide_image 0 0 x y (strcat cnp_root "/slides/scd3_11.sld"))
     (end_image)
    )
    ((= scd13_var_svis "scd13_vis_02")
     (setq scd13_type 2)
     (setq x (dimx_tile "scd_13_slide")
	   y (dimy_tile "scd_13_slide"))
     (start_image "scd_13_slide")
     (fill_image 0 0 x y -2)
     (slide_image 0 0 x y (strcat cnp_root "/slides/scd3_12.sld"))
     (end_image)
    )
  )
)   

;***********************************
;Configuração de Cores e Layers     
;***********************************
(defun scd13_laycol_button ()
  (scd13_last_writefile)
  (scd13_layc_file)
  (setq dcl_id (load_dialog (strcat cnp_root "/lisp/cadnorma.dcl")))
  (if (not (new_dialog "scd13_cfglayc" dcl_id)) (exit))
  ;degraus em vista
  (set_tile "scd13_layc_dvl" scd13_layc_dvl)
  (action_tile "scd13_layc_dvl" "(setq scd13_layc_dvl $value)")
  (start_image "scd13_layc_dvc")
  (fill_image  0  0
    (dimx_tile "scd13_layc_dvc")
    (dimy_tile "scd13_layc_dvc")
    (fix (distof scd13_layc_dvc))
  )
  (end_image)
  (action_tile "scd13_layc_dvc" "(scd13_layc_dvc_color)")
  ;degraus em projeção
  (set_tile "scd13_layc_dpl" scd13_layc_dpl)
  (action_tile "scd13_layc_dpl" "(setq scd13_layc_dpl $value)")
  (start_image "scd13_layc_dpc")
  (fill_image  0  0
    (dimx_tile "scd13_layc_dpc")
    (dimy_tile "scd13_layc_dpc")
    (fix (distof scd13_layc_dpc))
  )
  (end_image)
  (action_tile "scd13_layc_dpc" "(scd13_layc_dpc_color)")
  ;Corrimão
  (set_tile "scd13_layc_crl" scd13_layc_crl)
  (action_tile "scd13_layc_crl" "(setq scd13_layc_crl $value)")
  (start_image "scd13_layc_crc")
  (fill_image  0  0
    (dimx_tile "scd13_layc_crc")
    (dimy_tile "scd13_layc_crc")
    (fix (distof scd13_layc_crc))
  )
  (end_image)
  (action_tile "scd13_layc_crc" "(scd13_layc_crc_color)")
  ;ok_cancel
  (action_tile "cancel" "(done_dialog 0)")
  (action_tile "accept" "(done_dialog 1)")
  ;start_dialog
  (setq scd13_layc_id (start_dialog))
  (unload_dialog dcl_id)
  (if (= scd13_layc_id 1)
    (progn
      (scd13_layc_writefile)
      (scd13_main)
    )
  )
  (if (= scd13_layc_id 0) (scd13_main))
)

;escolher cor dos degraus em vista
(defun scd13_layc_dvc_color ()
  (setq scd13_layc_dvc_newcol (acad_colordlg (fix (distof scd13_layc_dvc))))
  (if (/= nil scd13_layc_dvc_newcol) (setq scd13_layc_dvc (rtos scd13_layc_dvc_newcol 2 0)))
  (start_image "scd13_layc_dvc")
  (fill_image  0  0
    (dimx_tile "scd13_layc_dvc")
    (dimy_tile "scd13_layc_dvc")
    (fix (distof scd13_layc_dvc))
  )
  (end_image)
)


;escolher cor dos degraus em projeção
(defun scd13_layc_dpc_color ()
  (setq scd13_layc_dpc_newcol (acad_colordlg (fix (distof scd13_layc_dpc))))
  (if (/= nil scd13_layc_dpc_newcol) (setq scd13_layc_dpc (rtos scd13_layc_dpc_newcol 2 0)))
  (start_image "scd13_layc_dpc")
  (fill_image  0  0
    (dimx_tile "scd13_layc_dpc")
    (dimy_tile "scd13_layc_dpc")
    (fix (distof scd13_layc_dpc))
  )
  (end_image)
)

;escolher cor do corrimão
(defun scd13_layc_crc_color ()
  (setq scd13_layc_crc_newcol (acad_colordlg (fix (distof scd13_layc_crc))))
  (if (/= nil scd13_layc_crc_newcol) (setq scd13_layc_crc (rtos scd13_layc_crc_newcol 2 0)))
  (start_image "scd13_layc_crc")
  (fill_image  0  0
    (dimx_tile "scd13_layc_crc")
    (dimy_tile "scd13_layc_crc")
    (fix (distof scd13_layc_crc))
  )
  (end_image)
)


;lê os dados iniciais da DCL no arquivo de dados
(defun scd13_layc_file ()
  (if (findfile (strcat cnp_root "/config/scd13_layc.txt"))
    (scd13_layc_readfile)
    (progn
      (setq file (open (strcat cnp_root "/config/scd13_layc.txt") "w" "utf8"))
      (write-line "Escada" file)
      (write-line "3" file)
      (write-line "Escada" file)
      (write-line "3" file)
      (write-line "Escada" file)
      (write-line "1" file)
      (close file)
      (scd13_layc_readfile)
    )
  )
)

;função que lê o arquivo de dados
(defun scd13_layc_readfile ()
  (setq	file (open (strcat cnp_root "/config/scd13_layc.txt") "r" "utf8"))
  (setq	scd13_layc_dvl (read-line file))
  (setq	scd13_layc_dvc (read-line file))
  (setq	scd13_layc_dpl (read-line file))
  (setq	scd13_layc_dpc (read-line file))
  (setq	scd13_layc_crl (read-line file))
  (setq	scd13_layc_crc (read-line file))
  (close file)
)

;função que escreve o arquivo de dados
(defun scd13_layc_writefile ()
  (setq	file (open (strcat cnp_root "/config/scd13_layc.txt") "w" "utf8"))
  (write-line scd13_layc_dvl file)
  (write-line scd13_layc_dvc file)
  (write-line scd13_layc_dpl file)
  (write-line scd13_layc_dpc file)
  (write-line scd13_layc_crl file)
  (write-line scd13_layc_crc file)
  (close file)
)

;clica em dois pontos = nova largura do degrau
(defun scd13_getdiai_button ()
  (scd13_last_writefile)
  (setq diai_dist nil
	pt1 (getpoint "\nPrimeiro ponto da diaiura... ")
	pt2 (getpoint pt1 "Segundo ponto da diaiura... ")
	diai_dist (distance pt1 pt2)
  )
  (cond
    ((= cn7_dwgunit 1.0) (setq new_dist (* diai_dist 100.0)))
    ((= cn7_dwgunit 100.0) (setq new_dist (* diai_dist 1.0)))
    ((= cn7_dwgunit 1000.0) (setq new_dist (* diai_dist 0.1)))
  )
  (if new_dist
    (progn
      (setq scd13_var_diai (rtos new_dist 2 2))
      (scd13_last_writefile)
    )
  )
  (scd13_main)
)

;clica em dois pontos = nova largura do degrau
(defun scd13_getldeg_button ()
  (scd13_last_writefile)
  (setq ldeg_dist nil
	pt1 (getpoint "\nPrimeiro ponto da ldegura... ")
	pt2 (getpoint pt1 "Segundo ponto da ldegura... ")
	ldeg_dist (distance pt1 pt2)
  )
  (cond
    ((= cn7_dwgunit 1.0) (setq new_dist (* ldeg_dist 100.0)))
    ((= cn7_dwgunit 100.0) (setq new_dist (* ldeg_dist 1.0)))
    ((= cn7_dwgunit 1000.0) (setq new_dist (* ldeg_dist 0.1)))
  )
  (if new_dist
    (progn
      (setq scd13_var_ldeg (rtos new_dist 2 2))
      (scd13_last_writefile)
    )
  )
  (scd13_main)
)

;clica em dois pontos = nova largura do degrau
(defun scd13_gethdeg_button ()
  (scd13_last_writefile)
  (setq hdeg_dist nil
	pt1 (getpoint "\nPrimeiro ponto da hdegura... ")
	pt2 (getpoint pt1 "Segundo ponto da hdegura... ")
	hdeg_dist (distance pt1 pt2)
  )
  (cond
    ((= cn7_dwgunit 1.0) (setq new_dist (* hdeg_dist 100.0)))
    ((= cn7_dwgunit 100.0) (setq new_dist (* hdeg_dist 1.0)))
    ((= cn7_dwgunit 1000.0) (setq new_dist (* hdeg_dist 0.1)))
  )
  (if new_dist
    (progn
      (setq scd13_var_hdeg (rtos new_dist 2 2))
      (scd13_last_writefile)
    )
  )
  (scd13_main)
)

;clica em dois pontos = nova altura do corrimão
(defun scd13_gethcor_button ()
  (scd13_last_writefile)
  (setq hcor_dist nil
	pt1 (getpoint "\nPrimeiro ponto da espessura... ")
	pt2 (getpoint pt1 "Segundo ponto da espessura... ")
	hcor_dist (distance pt1 pt2)
  )
  (cond
    ((= cn7_dwgunit 1.0) (setq new_dist (* hcor_dist 100.0)))
    ((= cn7_dwgunit 100.0) (setq new_dist (* hcor_dist 1.0)))
    ((= cn7_dwgunit 1000.0) (setq new_dist (* hcor_dist 0.1)))
  )
  (if new_dist
    (progn
      (setq scd13_var_hcor (rtos new_dist 2 2))
      (scd13_last_writefile)
    )
  )
  (scd13_main)
)


;clica em dois pontos = nova espessura da laje
(defun scd13_getllaj_button ()
  (scd13_last_writefile)
  (setq llaj_dist nil
	pt1 (getpoint "\nPrimeiro ponto da espessura... ")
	pt2 (getpoint pt1 "Segundo ponto da espessura... ")
	llaj_dist (distance pt1 pt2)
  )
  (cond
    ((= cn7_dwgunit 1.0) (setq new_dist (* llaj_dist 100.0)))
    ((= cn7_dwgunit 100.0) (setq new_dist (* llaj_dist 1.0)))
    ((= cn7_dwgunit 1000.0) (setq new_dist (* llaj_dist 0.1)))
  )
  (if new_dist
    (progn
      (setq scd13_var_llaj (rtos new_dist 2 2))
      (scd13_last_writefile)
    )
  )
  (scd13_main)
)

;verifica valor de entrada para diâmetro externo
(defun scd13_gethcor_action ()
  (setq scd13_var_newhcor $value)
  (if (distof scd13_var_newhcor)
    (setq scd13_var_hcor scd13_var_newhcor)
    (progn
      (alert "Valor Inválido!\nDigite um número Real.")
      (set_tile "scd13_gethcor" scd13_var_hcor)
      (mode_tile "scd13_gethcor" 2)
    )
  )
)


;verifica valor de entrada para largura da laje
(defun scd13_getllaj_action ()
  (setq scd13_var_newllaj $value)
  (if (distof scd13_var_newllaj)
    (setq scd13_var_llaj scd13_var_newllaj)
    (progn
      (alert "Valor Inválido!\nDigite um número Real.")
      (set_tile "scd13_getllaj" scd13_var_llaj)
      (mode_tile "scd13_getllaj" 2)
    )
  )
)

;verifica se o valor entrado é válido para número de degraus
(defun scd13_getndeg_action ()
  (setq scd13_var_newndeg $value)
  (if (and (distof scd13_var_newndeg) (= (distof scd13_var_newndeg) (fix (distof scd13_var_newndeg))))
    (progn
      (setq scd13_var_ndeg scd13_var_newndeg)
    )
    (progn
      (alert "Valor Inválido!\nDigite um número inteiro.")
      (set_tile "scd13_getndeg" scd13_var_ndeg)
      (mode_tile "scd13_getndeg" 2)
    )
  )
)

;verifica valor de entrada para largura do degrau
(defun scd13_getldeg_action ()
  (setq scd13_var_newldeg $value)
  (if (distof scd13_var_newldeg)
    (setq scd13_var_ldeg scd13_var_newldeg)
    (progn
      (alert "Valor Inválido!\nDigite um número Real.")
      (set_tile "scd13_getldeg" scd13_var_ldeg)
      (mode_tile "scd13_getldeg" 2)
    )
  )
)

;verifica valor de entrada para diâmetro externo
(defun scd13_gethdeg_action ()
  (setq scd13_var_newhdeg $value)
  (if (distof scd13_var_newhdeg)
    (setq scd13_var_hdeg scd13_var_newhdeg)
    (progn
      (alert "Valor Inválido!\nDigite um número Real.")
      (set_tile "scd13_gethdeg" scd13_var_hdeg)
      (mode_tile "scd13_gethdeg" 2)
    )
  )
)

;lê os dados iniciais da DCL no arquivo de dados
(defun scd13_last_file ()
  (if (findfile (strcat cnp_root "/config/scd13_last.txt"))
    (scd13_last_readfile)
    (progn
      (setq file (open (strcat cnp_root "/config/scd13_last.txt") "w" "utf8"))
      (write-line "28" file)
      (write-line "18.75" file)
      (write-line "8" file)
      (write-line "10" file)
      (write-line "1" file)
      (write-line "110" file)
      (write-line "scd13_vis_02" file)
      (close file)
      (scd13_last_readfile)
    )
  )
)

;função que lê o arquivo de dados
(defun scd13_last_readfile ()
  (setq	file (open (strcat cnp_root "/config/scd13_last.txt") "r" "utf8"))
  (setq	scd13_var_ldeg (read-line file))
  (setq	scd13_var_hdeg (read-line file))
  (setq	scd13_var_ndeg (read-line file))
  (setq	scd13_var_llaj (read-line file))
  (setq	scd13_var_dcor (read-line file))
  (setq	scd13_var_hcor (read-line file))
  (setq	scd13_var_svis (read-line file))
  (close file)
)

;função que escreve o arquivo de dados
(defun scd13_last_writefile ()
  (setq	file (open (strcat cnp_root "/config/scd13_last.txt") "w" "utf8"))
  (write-line scd13_var_ldeg file)
  (write-line scd13_var_hdeg file)
  (write-line scd13_var_ndeg file)
  (write-line scd13_var_llaj file)
  (write-line scd13_var_dcor file)
  (write-line scd13_var_hcor file)
  (write-line scd13_var_svis file)
  (close file)
)

;procedimento inicial para escadas
(defun scd13_start ()
  (cn7_init)
  (guarda '("blipmode" "cecolor" "celtype" "clayer" "cmdecho" "orthomode"
          "textstyle" "luprec" "osmode" ))
  (setvar "cecolor" "bylayer")
  (scd13_last_file)
  (scd13_layc_file)
  (cond
    ((= cn7_dwgunit 1) (setq scd13_fator 0.01 scd13_blkscl 1.0))
    ((= cn7_dwgunit 100) (setq scd13_fator 1.0 scd13_blkscl 100.0))
    ((= cn7_dwgunit 1000) (setq scd13_fator 10.0 scd13_blkscl 1000.0))
  )
)


;cnp_21_d_janelas

;Cadnorma Professional
;iniciado em 10/12/10
;programa de janelas
(defun c:jn ()
  ;arquivo inicial
  (jnl_last_file)
  (jnl_main)
)

;aber a DCL principal
(defun jnl_main ()
  (cn7_init)
  ;abre a caixa de diálogo
  (setq dcl_id (load_dialog (strcat cnp_root "/lisp/cadnorma.dcl")))
  (if (not (new_dialog "janela" dcl_id)) (exit))
  ;atualização de slides
  (jnl_update_slides)
    (if
    (or (= "31" jnl_var_tipo) (= "32" jnl_var_tipo) (= "33" jnl_var_tipo) (= "34" jnl_var_tipo)
	(= "41" jnl_var_tipo) (= "42" jnl_var_tipo) (= "43" jnl_var_tipo) (= "44" jnl_var_tipo))
    (mode_tile "jnl_cfg_detype" 0)
    (mode_tile "jnl_cfg_detype" 1)
  )
  ;largura em retângulos
  (set_tile "jnl_getlarg_edit" jnl_var_larg)
  (action_tile "jnl_getlarg_edit" "(jnl_getlarg_editaction)")
  (action_tile "jnl_getlarg_pick" "(done_dialog 2)")
  ;largura em diâmetros
  (set_tile "jnl_getdiam_edit" jnl_var_diam)
  (action_tile "jnl_getdiam_edit" "(jnl_getdiam_editaction)")
  ;lista de alturas
  (jnl_halt_file)
  (start_list "jnl_dcl_halt")
  (mapcar 'add_list jnl_halt_list)
  (end_list)
  (set_tile "jnl_dcl_halt" jnl_var_halt)
  (action_tile "jnl_dcl_halt" "(setq jnl_var_halt $value)")
  (action_tile "jnl_halt_edit" "(done_dialog 3)")
  ;Definições por opção de largura
  (jnl_larg_def)
  (action_tile "jnl_larg_radio1" "(jnl_larg_radio_action)")
  (action_tile "jnl_larg_radio2" "(jnl_larg_radio_action)")
  (action_tile "jnl_getdiam_pick" "(done_dialog 4)")
  ;slide do Tipo Atual
  (setq x (dimx_tile "jnl_slide_type")
	y (dimy_tile "jnl_slide_type")
  )
  (start_image "jnl_slide_type")
  (fill_image 0 0 x y -2)
  (slide_image 0 0 x y (strcat cnp_root "/slides/jnl_" jnl_var_tipo ".sld"))
  (end_image)
;;;  ;Posicionamento
  (set_tile "jnl_posi" jnl_var_posi)
  (if (= "jnl_center" jnl_var_posi)
    (mode_tile "jnl_afas_edit" 1)
    (mode_tile "jnl_afas_edit" 0)
  )
  (action_tile "jnl_posi" "(jnl_posi_action)")
  ;afastamento
  (set_tile "jnl_afas_edit" jnl_var_afas)
  (action_tile "jnl_afas_edit" "(jnl_getafas_editaction)")
  (action_tile "jnl_get_afas" "(done_dialog 5)")
  ;parede
  (set_tile "jnl_wall_edit" jnl_var_wall)
  (action_tile "jnl_wall_edit" "(jnl_getwall_editaction)")
  (action_tile "jnl_get_wall" "(done_dialog 6)")
  ;caixilho
  (set_tile "jnl_caix_edit" jnl_var_caix)
  (action_tile "jnl_caix_edit" "(jnl_getcaix_editaction)")
  (action_tile "jnl_get_caix" "(done_dialog 7)")
  ;código de identificação
  (set_tile "jnl_iden_toggle" jnl_var_iden)
  (action_tile "jnl_iden_toggle" "(setq jnl_var_iden $value)")
  (action_tile "jnl_iden_button" "(done_dialog 8)")
  (action_tile "jnl_cfg_laycol" "(done_dialog 9)")
  (action_tile "cancel" "(done_dialog 0)")
  (action_tile "accept" "(done_dialog 1)")
  ;ativação da DCL
  (setq jnl_dcl_id (start_dialog))
  (unload_dialog dcl_id)
  ;ações dos botões
  (if (= 1 jnl_dcl_id) (jnl_ok_action))
  (if (= 2 jnl_dcl_id) (jnl_getlarg_button))
  (if (= 3 jnl_dcl_id) (jnl_haltedit_action))
  (if (= 4 jnl_dcl_id) (jnl_getdiam_button))
  (if (= 5 jnl_dcl_id) (jnl_getafas_button))
  (if (= 6 jnl_dcl_id) (jnl_getwall_button))
  (if (= 7 jnl_dcl_id) (jnl_getcaix_button))
  (if (= 8 jnl_dcl_id) (jnl_cfgiden_button))
  (if (= 9 jnl_dcl_id) (jnl_laycol_button))
  (princ)
)


;***********************************
;Configuração de Cores e Layers     
;***********************************
(defun jnl_laycol_button ()
  (jnl_layc_file)
  (setq dcl_id (load_dialog (strcat cnp_root "/lisp/cadnorma.dcl")))
  (if (not (new_dialog "jnl_cfglayc" dcl_id)) (exit))
  ;caixilho
  (set_tile "jnl_layc_cxl" jnl_layc_cxl)
  (action_tile "jnl_layc_cxl" "(setq jnl_layc_cxl $value)")
  (start_image "jnl_layc_cxc")
  (fill_image  0  0
    (dimx_tile "jnl_layc_cxc")
    (dimy_tile "jnl_layc_cxc")
    (fix (distof jnl_layc_cxc))
  )
  (end_image)
  (action_tile "jnl_layc_cxc" "(jnl_layc_cxc_color)")
  ;Vista
  (set_tile "jnl_layc_vil" jnl_layc_vil)
  (action_tile "jnl_layc_vil" "(setq jnl_layc_vil $value)")
  (start_image "jnl_layc_vic")
  (fill_image  0  0
    (dimx_tile "jnl_layc_vic")
    (dimy_tile "jnl_layc_vic")
    (fix (distof jnl_layc_vic))
  )
  (end_image)
  (action_tile "jnl_layc_vic" "(jnl_layc_vic_color)")
  ;Projeção
  (set_tile "jnl_layc_prl" jnl_layc_prl)
  (action_tile "jnl_layc_prl" "(setq jnl_layc_prl $value)")
  (start_image "jnl_layc_prc")
  (fill_image  0  0
    (dimx_tile "jnl_layc_prc")
    (dimy_tile "jnl_layc_prc")
    (fix (distof jnl_layc_prc))
  )
  (end_image)
  (action_tile "jnl_layc_prc" "(jnl_layc_prc_color)")
  ;Parapeito
  (set_tile "jnl_layc_ppl" jnl_layc_ppl)
  (action_tile "jnl_layc_ppl" "(setq jnl_layc_ppl $value)")
  (start_image "jnl_layc_ppc")
  (fill_image  0  0
    (dimx_tile "jnl_layc_ppc")
    (dimy_tile "jnl_layc_ppc")
    (fix (distof jnl_layc_ppc))
  )
  (end_image)
  (action_tile "jnl_layc_ppc" "(jnl_layc_ppc_color)")
  ;ok_cancel
  (action_tile "cancel" "(done_dialog 0)")
  (action_tile "accept" "(done_dialog 1)")
  ;start_dialog
  (setq jnl_layc_id (start_dialog))
  (unload_dialog dcl_id)
  (if (= jnl_layc_id 1)
    (progn
      (jnl_layc_writefile)
      (jnl_main)
    )
  )
  (if (= jnl_layc_id 0) (jnl_main))
)

;escolher cor da Projeção
(defun jnl_layc_prc_color ()
  (setq jnl_layc_prc_newcol (acad_colordlg (fix (distof jnl_layc_prc))))
  (if (/= nil jnl_layc_prc_newcol) (setq jnl_layc_prc (rtos jnl_layc_prc_newcol 2 0)))
  (start_image "jnl_layc_prc")
  (fill_image  0  0
    (dimx_tile "jnl_layc_prc")
    (dimy_tile "jnl_layc_prc")
    (fix (distof jnl_layc_prc))
  )
  (end_image)
)


;escolher cor da janela em vista
(defun jnl_layc_vic_color ()
  (setq jnl_layc_vic_newcol (acad_colordlg (fix (distof jnl_layc_vic))))
  (if (/= nil jnl_layc_vic_newcol) (setq jnl_layc_vic (rtos jnl_layc_vic_newcol 2 0)))
  (start_image "jnl_layc_vic")
  (fill_image  0  0
    (dimx_tile "jnl_layc_vic")
    (dimy_tile "jnl_layc_vic")
    (fix (distof jnl_layc_vic))
  )
  (end_image)
)

;escolher cor do caixilho
(defun jnl_layc_cxc_color ()
  (setq jnl_layc_cxc_newcol (acad_colordlg (fix (distof jnl_layc_cxc))))
  (if (/= nil jnl_layc_cxc_newcol) (setq jnl_layc_cxc (rtos jnl_layc_cxc_newcol 2 0)))
  (start_image "jnl_layc_cxc")
  (fill_image  0  0
    (dimx_tile "jnl_layc_cxc")
    (dimy_tile "jnl_layc_cxc")
    (fix (distof jnl_layc_cxc))
  )
  (end_image)
)


;escolher cor do parapeito
(defun jnl_layc_ppc_color ()
  (setq jnl_layc_ppc_newcol (acad_colordlg (fix (distof jnl_layc_ppc))))
  (if (/= nil jnl_layc_ppc_newcol) (setq jnl_layc_ppc (rtos jnl_layc_ppc_newcol 2 0)))
  (start_image "jnl_layc_ppc")
  (fill_image  0  0
    (dimx_tile "jnl_layc_ppc")
    (dimy_tile "jnl_layc_ppc")
    (fix (distof jnl_layc_ppc))
  )
  (end_image)
)


;lê os dados iniciais da DCL no arquivo de dados
(defun jnl_layc_file ()
  (if (findfile (strcat cnp_root "/config/jnl_layc.txt"))
    (jnl_layc_readfile)
    (progn
      (setq file (open (strcat cnp_root "/config/jnl_layc.txt") "w" "utf8"))
      (write-line "Janela" file)
      (write-line "3" file)
      (write-line "Janela" file)
      (write-line "3" file)
      (write-line "Janela" file)
      (write-line "1" file)
      (write-line "Janela" file)
      (write-line "1" file)
      (close file)
      (jnl_layc_readfile)
    )
  )
)

;função que lê o arquivo de dados
(defun jnl_layc_readfile ()
  (setq	file (open (strcat cnp_root "/config/jnl_layc.txt") "r" "utf8"))
  (setq	jnl_layc_cxl (read-line file))
  (setq	jnl_layc_cxc (read-line file))
  (setq	jnl_layc_vil (read-line file))
  (setq	jnl_layc_vic (read-line file))
  (setq	jnl_layc_prl (read-line file))
  (setq	jnl_layc_prc (read-line file))
  (setq	jnl_layc_ppl (read-line file))
  (setq	jnl_layc_ppc (read-line file))
  (close file)
)

;função que escreve o arquivo de dados
(defun jnl_layc_writefile ()
  (setq	file (open (strcat cnp_root "/config/jnl_layc.txt") "w" "utf8"))
  (write-line jnl_layc_cxl file)
  (write-line jnl_layc_cxc file)
  (write-line jnl_layc_vil file)
  (write-line jnl_layc_vic file)
  (write-line jnl_layc_prl file)
  (write-line jnl_layc_prc file)
  (write-line jnl_layc_ppl file)
  (write-line jnl_layc_ppc file)
  (close file)
)


;***********************************
;Configuração de Identificação      
;***********************************

;caixa de diálogo
(defun jnl_cfgiden_button ()
  (jnl_iden_file)
  (setq dcl_id (load_dialog (strcat cnp_root "/lisp/cadnorma.dcl")))
  (if (not (new_dialog "jnl_cfgiden" dcl_id)) (exit))
  ;preenche os slides
  (jnl_iden_upslides)
  (setq x (dimx_tile "jnl_cfgiden_typ")
	y (dimy_tile "jnl_cfgiden_typ"))
  (start_image "jnl_cfgiden_typ")
  (fill_image  0 0 x y -2)
  (slide_image 0 0 x y (strcat cnp_root "/slides/jnl_iden" jnl_iden_typ ".sld"))
  (end_image)
  ;estilos de texto
  (setq jnl_iden_stylist (list "r50" "r60" "r70" "r80" "r90" "r100" "r120" "r140" "r175" "r200"
			       "t1" "t2" "t3" "t4" "t5" "t6" "t7"))
  (start_list "jnl_cfgiden_sty")
  (mapcar 'add_list jnl_iden_stylist)
  (end_list)
  (set_tile "jnl_cfgiden_sty" jnl_iden_sty)
  (action_tile "jnl_cfgiden_sty" "(setq jnl_iden_sty $value)")
  ;cor dos elementos
  (start_image "jnl_cfgiden_col")
  (fill_image  0  0
    (dimx_tile "jnl_cfgiden_col")
    (dimy_tile "jnl_cfgiden_col")
    (fix (distof jnl_iden_col))
  )
  (end_image)
  (action_tile "jnl_cfgiden_col" "(jnl_idencol_action)")
  ;layer da identificação
  (set_tile "jnl_cfgiden_lay" jnl_iden_lay)
  (action_tile "jnl_cfgiden_lay" "(setq jnl_iden_lay $value)")
  ;botões principais
  (action_tile "cancel" "(done_dialog 0)")
  (action_tile "accept" "(done_dialog 1)")
  (setq jnl_idendcl_id (start_dialog))
  (unload_dialog dcl_id)
  (if (= 1 jnl_idendcl_id) (jnl_iden_writefile))
  (jnl_main)
)


;escolher a cor do identificador
(defun jnl_idencol_action ()
  (setq jnl_iden_newcol (acad_colordlg (fix (distof jnl_iden_col))))
  (if (/= nil jnl_iden_newcol) (setq jnl_iden_col (rtos jnl_iden_newcol 2 0)))
  (start_image "jnl_cfgiden_col")
  (fill_image  0  0
    (dimx_tile "jnl_cfgiden_col")
    (dimy_tile "jnl_cfgiden_col")
    (fix (distof jnl_iden_col))
  )
  (end_image)
)


;atualiza os slides a atribui actions
(defun jnl_iden_upslides ()
  (setq x (dimx_tile "iden11")
	y (dimy_tile "iden11"))
  (start_image "iden11")
  (slide_image 0 0 x y (strcat cnp_root "/slides/jnl_iden11.sld"))
  (end_image)
  (action_tile "iden11" "(jnl_cfgiden_seltype)")
  (setq x (dimx_tile "iden12")
	y (dimy_tile "iden12"))
  (start_image "iden12")
  (slide_image 0 0 x y (strcat cnp_root "/slides/jnl_iden12.sld"))
  (end_image)
  (action_tile "iden12" "(jnl_cfgiden_seltype)")
  (setq x (dimx_tile "iden13")
	y (dimy_tile "iden13"))
  (start_image "iden13")
  (slide_image 0 0 x y (strcat cnp_root "/slides/jnl_iden13.sld"))
  (end_image)
  (action_tile "iden13" "(jnl_cfgiden_seltype)")
  (setq x (dimx_tile "iden21")
	y (dimy_tile "iden21"))
  (start_image "iden21")
  (slide_image 0 0 x y (strcat cnp_root "/slides/jnl_iden21.sld"))
  (end_image)
  (action_tile "iden21" "(jnl_cfgiden_seltype)")
  (setq x (dimx_tile "iden22")
	y (dimy_tile "iden22"))
  (start_image "iden22")
  (slide_image 0 0 x y (strcat cnp_root "/slides/jnl_iden22.sld"))
  (end_image)
  (action_tile "iden22" "(jnl_cfgiden_seltype)")
  (setq x (dimx_tile "iden23")
	y (dimy_tile "iden23"))
  (start_image "iden23")
  (slide_image 0 0 x y (strcat cnp_root "/slides/jnl_iden23.sld"))
  (end_image)
  (action_tile "iden23" "(jnl_cfgiden_seltype)")
)

;ao selecionar um slide
(defun jnl_cfgiden_seltype ()
  (setq jnl_iden_tipo $key
	jnl_iden_typ (substr jnl_iden_tipo 5 2)
  )
  (setq x (dimx_tile "jnl_cfgiden_typ")
	y (dimy_tile "jnl_cfgiden_typ"))
  (start_image "jnl_cfgiden_typ")
  (fill_image  0 0 x y -2)
  (slide_image 0 0 x y (strcat cnp_root "/slides/jnl_iden" jnl_iden_typ ".sld"))
  (end_image)
)


;lê os dados iniciais da DCL no arquivo de dados
(defun jnl_iden_file ()
  (if (findfile (strcat cnp_root "/config/jnl_iden.txt"))
    (jnl_iden_readfile)
    (progn
      (setq file (open (strcat cnp_root "/config/jnl_iden.txt") "w" "utf8"))
      (write-line "11" file)
      (write-line "5" file)
      (write-line "2" file)
      (write-line "Janela_ident" file)
      (close file)
      (jnl_iden_readfile)
    )
  )
)

;função que lê o arquivo de dados
(defun jnl_iden_readfile ()
  (setq	file (open (strcat cnp_root "/config/jnl_iden.txt") "r" "utf8"))
  (setq	jnl_iden_typ (read-line file))
  (setq	jnl_iden_sty (read-line file))
  (setq	jnl_iden_col (read-line file))
  (setq	jnl_iden_lay (read-line file))
  (close file)
)

;função que escreve o arquivo de dados
(defun jnl_iden_writefile ()
  (setq	file (open (strcat cnp_root "/config/jnl_iden.txt") "w" "utf8"))
  (write-line jnl_iden_typ file)
  (write-line jnl_iden_sty file)
  (write-line jnl_iden_col file)
  (write-line jnl_iden_lay file)
  (close file)
)

;***********************************
;Configuração de Caixilho           
;***********************************
(defun jnl_getcaix_button ()
  (jnl_last_writefile)
  (setq caix_dist nil
	pt1 (getpoint "\nPrimeiro ponto da parede...: ")
	pt2 (getpoint pt1 "Segundo ponto da parede... ")
	caix_dist (distance pt1 pt2)
  )
  (cond
    ((= cn7_dwgunit 1.0) (setq new_dist (* caix_dist 100.0)))
    ((= cn7_dwgunit 100.0) (setq new_dist (* caix_dist 1.0)))
    ((= cn7_dwgunit 1000.0) (setq new_dist (* caix_dist 0.1)))
  )
  (if new_dist
    (progn
      (setq jnl_var_caix (rtos new_dist 2 2))
      (jnl_last_writefile)
    )
  )
  (jnl_main)
)

;verifica se o valor entrado é válido
(defun jnl_getcaix_editaction ()
  (setq jnl_var_newcaix $value)
  (if (distof jnl_var_newcaix)
    (setq jnl_var_caix jnl_var_newcaix)
    (progn
      (alert "Valor Inválido!")
      (set_tile "jnl_caix_edit" jnl_var_caix)
      (mode_tile "jnl_caix_edit" 2)
    )
  )
)  


;***********************************
;Espessura de Paredes               
;***********************************

;clica em dois pontos = nova espessura de paredes
(defun jnl_getwall_button ()
  (jnl_last_writefile)
  (setq wall_dist nil
	pt1 (getpoint "\nPrimeiro ponto da parede...: ")
	pt2 (getpoint pt1 "Segundo ponto da parede... ")
	wall_dist (distance pt1 pt2)
  )
  (cond
    ((= cn7_dwgunit 1.0) (setq new_dist (* wall_dist 100.0)))
    ((= cn7_dwgunit 100.0) (setq new_dist (* wall_dist 1.0)))
    ((= cn7_dwgunit 1000.0) (setq new_dist (* wall_dist 0.1)))
  )
  (if new_dist
    (progn
      (setq jnl_var_wall (rtos new_dist 2 2))
      (jnl_last_writefile)
    )
  )
  (jnl_main)
)
  

;verifica se o valor entrado é válido para espessura de parede
(defun jnl_getwall_editaction ()
  (setq jnl_var_newwall $value)
  (if (distof jnl_var_newwall)
    (setq jnl_var_wall jnl_var_newwall)
    (progn
      (alert "Valor Inválido!")
      (set_tile "jnl_wall_edit" jnl_var_wall)
      (mode_tile "jnl_wall_edit" 2)
    )
  )
)  


;***********************************
;Posicionamento e Afastamento       
;***********************************

;clica em dois pontos = novo afastamento
(defun jnl_getafas_button ()
  (jnl_last_writefile)
  (setq afas_dist nil
	pt1 (getpoint "\nPrimeiro ponto do afastamento...: ")
	pt2 (getpoint pt1 "Segundo ponto do afastamento... ")
	afas_dist (distance pt1 pt2)
  )
  (cond
    ((= cn7_dwgunit 1.0) (setq new_dist (* afas_dist 100.0)))
    ((= cn7_dwgunit 100.0) (setq new_dist (* afas_dist 1.0)))
    ((= cn7_dwgunit 1000.0) (setq new_dist (* afas_dist 0.1)))
  )
  (if new_dist
    (progn
      (setq jnl_var_afas (rtos new_dist 2 2))
      (jnl_last_writefile)
    )
  )
  (jnl_main)
)

;ao selecionar a posição da porta
(defun jnl_posi_action ()
  (setq jnl_var_posi $value)
  (if (= "jnl_center" jnl_var_posi)
    (mode_tile "jnl_afas_edit" 1)
    (progn
      (mode_tile "jnl_afas_edit" 0)
      (mode_tile "jnl_afas_edit" 2)
    )
  )
)

;verifica se o valor entrado é válido
(defun jnl_getafas_editaction ()
  (setq jnl_var_newafas $value)
  (if (distof jnl_var_newafas)
    (setq jnl_var_afas jnl_var_newafas)
    (progn
      (alert "Valor Inválido!")
      (set_tile "jnl_afas_edit" jnl_var_afas)
      (mode_tile "jnl_afas_edit" 2)
    )
  )
)  

;********************
;LARGURAS
;********************

;verifica se o valor entrado é válido para diâmetro
(defun jnl_getdiam_editaction ()
  (setq jnl_var_newdiam $value)
  (if (distof jnl_var_newdiam)
    (setq jnl_var_diam jnl_var_newdiam)
    (progn
      (alert "Valor Inválido!")
      (set_tile "jnl_getdiam_edit" jnl_var_diam)
      (mode_tile "jnl_getdiam_edit" 2)
    )
  )
)  

;ao selecionar o rádio 1 ou 2
(defun jnl_larg_radio_action ()
  (setq jnl_var_lrad $key)
  (jnl_larg_def)
  (if (= jnl_var_lrad "jnl_larg_radio2")
    (mode_tile "jnl_getlarg_edit" 2)
  )
)

;método de determinação da largura
(defun jnl_larg_def ()
  (if (= jnl_var_lrad "jnl_larg_radio1")
    (progn
      (set_tile "jnl_larg_radio1" "1")
      (set_tile "jnl_larg_radio2" "0")
      (mode_tile "jnl_getlarg_edit" 0)
      (mode_tile "jnl_getlarg_pick" 0)
      (mode_tile "jnl_dcl_halt" 0)
      (mode_tile "jnl_halt_edit" 0)
      (mode_tile "jnl_getdiam_edit" 1)
      (mode_tile "jnl_getdiam_pick" 1)
;;;      (mode_tile "jnl_getlarg_edit" 2)
    )
    (progn
      (set_tile "jnl_larg_radio1" "0")
      (set_tile "jnl_larg_radio2" "1")
      (mode_tile "jnl_getlarg_edit" 1)
      (mode_tile "jnl_getlarg_pick" 1)
      (mode_tile "jnl_dcl_halt" 1)
      (mode_tile "jnl_halt_edit" 1)
      (mode_tile "jnl_getdiam_edit" 0)
      (mode_tile "jnl_getdiam_edit" 2)
      (mode_tile "jnl_getdiam_pick" 0)
    )
  )
)

  
;********************
;Alturas             
;********************

;edição de alturas
(defun jnl_haltedit_action ()
  (setq jnl_cfghalt_sel jnl_var_halt)
  (setq dcl_id (load_dialog (strcat cnp_root "/lisp/cadnorma.dcl")))
  (if (not (new_dialog "jnl_edit_halt" dcl_id)) (exit))
  (jnl_halt_file);-> jnl_halt_list
  (start_list "jnl_cfghalt_list")
  (mapcar 'add_list jnl_halt_list)
  (end_list)
  (set_tile "jnl_cfghalt_list" jnl_cfghalt_sel)
;;;  (cond
;;;    ((= "0" jnl_cfghalt_sel)
;;;     (mode_tile "jnl_cfghalt_up" 1)
;;;     (mode_tile "jnl_cfghalt_down" 0)
;;;    )
;;;    ((= jnl_cfghalt_sel (rtos (1- halt_list_len) 2 0))
;;;     (mode_tile "jnl_cfghalt_up" 0)
;;;     (mode_tile "jnl_cfghalt_down" 1)
;;;    )
;;;    (t
;;;     (mode_tile "jnl_cfghalt_up" 0)
;;;     (mode_tile "jnl_cfghalt_down" 0)
;;;    )     
;;;  )
  (action_tile "jnl_cfghalt_list" "(jnl_cfghalt_selist)")
  (action_tile "jnl_cfghalt_up" "(jnl_cfghalt_up)")
  (action_tile "jnl_cfghalt_down" "(jnl_cfghalt_down)")
  (action_tile "cancel" "(done_dialog 0)")
  (action_tile "accept" "(done_dialog 1)")
  (action_tile "jnl_cfghalt_add" "(done_dialog 2)")
  (action_tile "jnl_cfghalt_del" "(jnl_cfghalt_delete)")
  (setq jnl_halt_dclid (start_dialog))
  (unload_dialog dcl_id)
  (if (= 0 jnl_halt_dclid) (jnl_main))
  (if (= 1 jnl_halt_dclid) (jnl_cfghalt_ok))
  (if (= 2 jnl_halt_dclid) (jnl_cfghalt_addaction))
)


;Arquivos de configuração de alturas
(defun jnl_halt_file ()
  (if (findfile (strcat cnp_root "/config/jnl_altura.txt"))
    (jnl_halt_readfile)
    (progn
      (setq file (open (strcat cnp_root "/config/jnl_altura.txt") "w" "utf8"))
      (write-line "60" file)
      (write-line "80" file)
      (write-line "90" file)
      (write-line "100" file)
      (write-line "110" file)
      (write-line "120" file)
      (close file)
      (jnl_halt_readfile)
    )
  )
)

;lâ a lista de alturas disponíveis
(defun jnl_halt_readfile ()
  (setq file (open (strcat cnp_root "/config/jnl_altura.txt") "r" "utf8"))
  (setq jnl_halt_list (list))
  (while (/= nil (setq linha (read-line file)))
    (setq jnl_halt_list (append jnl_halt_list (list linha)))
  )
  (close file)
)

;escreve a lista de alturas disponíveis
(defun jnl_halt_writefile ()
  (setq file (open (strcat cnp_root "/config/jnl_altura.txt") "w" "utf8"))
  (foreach n jnl_halt_list
    (write-line n file)
  )
  (close file)
)


;botão ok
(defun jnl_cfghalt_ok ()
  (jnl_halt_writefile)
  (jnl_main)
)

;botão Excluir
(defun jnl_cfghalt_delete ()
  (setq counter 0
	halt_list_len (length jnl_halt_list)
	new_list (list)
  )
  (repeat halt_list_len
    (if (/= counter (fix (distof jnl_cfghalt_sel)))
      (setq new_list (append new_list (list (nth counter jnl_halt_list))))
    )
    (setq counter (1+ counter))
  )
  (setq jnl_halt_list new_list)
  (start_list "jnl_cfghalt_list")
  (mapcar 'add_list jnl_halt_list)
  (end_list)
  (set_tile "jnl_cfghalt_list" jnl_cfghalt_sel)
)
	    

;botão Adicionar
(defun jnl_cfghalt_addaction ()
  (setq jnl_gethalt_nova nil)
  (setq dcl_id (load_dialog (strcat cnp_root "/lisp/cadnorma.dcl")))
  (if (not (new_dialog "jnl_halt_getnew" dcl_id)) (exit))
  (mode_tile "jnl_halt_getnew_edit" 2)
  (action_tile "jnl_halt_getnew_edit" "(setq jnl_gethalt_nova $value)")
  (action_tile "cancel" "(done_dialog 0)")
  (action_tile "accept" "(done_dialog 1)")
  (setq jnl_gethalt_dclid (start_dialog))
  (unload_dialog dcl_id)
  (if (= 1 jnl_gethalt_dclid)
    (if (and (/= nil jnl_gethalt_nova)
	     (/= "" jnl_gethalt_nova)
	     (distof jnl_gethalt_nova)
	)
      (progn
	(setq jnl_halt_list (append jnl_halt_list (list jnl_gethalt_nova)))
	(jnl_halt_writefile)
	(jnl_halt_file)
        (jnl_haltedit_action)
      )
    )
  )
)

;ao selecionar um item da lista
(defun jnl_cfghalt_selist ()
  (setq jnl_cfghalt_sel $value
	halt_list_len (length jnl_halt_list)
  )
  (cond
    ((= "0" jnl_cfghalt_sel)
     (mode_tile "jnl_cfghalt_up" 1)
     (mode_tile "jnl_cfghalt_down" 0)
    )
    ((= jnl_cfghalt_sel (rtos (1- halt_list_len) 2 0))
     (mode_tile "jnl_cfghalt_up" 0)
     (mode_tile "jnl_cfghalt_down" 1)
    )
    (t
     (mode_tile "jnl_cfghalt_up" 0)
     (mode_tile "jnl_cfghalt_down" 0)
    )     
  )
)

;ação para o botão "up"
(defun jnl_cfghalt_up ()
  (setq halt_1 (fix (distof jnl_cfghalt_sel));selecionado
	halt_2 (1- halt_1);subir
	counter 0
	new_list2 (list))
  (while (< counter (length jnl_halt_list))
    (if (= counter halt_2)
      (progn
	(setq new_list2 (append new_list2 (list (nth (1+ counter) jnl_halt_list))))
	(setq new_list2 (append new_list2 (list (nth counter jnl_halt_list))))
	(setq counter (+ 2 counter))
      )
      (progn
	(setq new_list2 (append new_list2 (list (nth counter jnl_halt_list))))
	(setq counter (1+ counter))
      )
    )
  )
  (setq jnl_halt_list new_list2)
  (start_list "jnl_cfghalt_list")
  (mapcar 'add_list jnl_halt_list)
  (end_list)
  (setq jnl_cfghalt_sel (rtos (1- (fix (distof jnl_cfghalt_sel))) 2 0))
  (set_tile "jnl_cfghalt_list" jnl_cfghalt_sel)
  (cond
    ((= "0" jnl_cfghalt_sel)
     (mode_tile "jnl_cfghalt_up" 1)
     (mode_tile "jnl_cfghalt_down" 0)
    )
    ((= jnl_cfghalt_sel (rtos (1- halt_list_len) 2 0))
     (mode_tile "jnl_cfghalt_up" 0)
     (mode_tile "jnl_cfghalt_down" 1)
    )
    (t
     (mode_tile "jnl_cfghalt_up" 0)
     (mode_tile "jnl_cfghalt_down" 0)
    )     
  )
)

;ação para o botão "down"
(defun jnl_cfghalt_down ()
  (setq halt_1 (fix (distof jnl_cfghalt_sel));selecionado
	halt_2 (1+ halt_1);subir
	counter 0
	new_list2 (list))
  (while (< counter (length jnl_halt_list))
    (if (= counter halt_1)
      (progn
	(setq new_list2 (append new_list2 (list (nth (1+ counter) jnl_halt_list))))
	(setq new_list2 (append new_list2 (list (nth counter jnl_halt_list))))
	(setq counter (+ 2 counter))
      )
      (progn
	(setq new_list2 (append new_list2 (list (nth counter jnl_halt_list))))
	(setq counter (1+ counter))
      )
    )
  )
  (setq jnl_halt_list new_list2)
  (start_list "jnl_cfghalt_list")
  (mapcar 'add_list jnl_halt_list)
  (end_list)
  (setq jnl_cfghalt_sel (rtos (1+ (fix (distof jnl_cfghalt_sel))) 2 0))
  (set_tile "jnl_cfghalt_list" jnl_cfghalt_sel)
  (cond
    ((= "0" jnl_cfghalt_sel)
     (mode_tile "jnl_cfghalt_up" 1)
     (mode_tile "jnl_cfghalt_down" 0)
    )
    ((= jnl_cfghalt_sel (rtos (1- halt_list_len) 2 0))
     (mode_tile "jnl_cfghalt_up" 0)
     (mode_tile "jnl_cfghalt_down" 1)
    )
    (t
     (mode_tile "jnl_cfghalt_up" 0)
     (mode_tile "jnl_cfghalt_down" 0)
    )     
  )
)

;***********************************
;LARGURA                            
;***********************************

;clica em dois pontos = novo diâmetro
(defun jnl_getdiam_button ()
  (jnl_last_writefile)
  (setq diam_dist nil
	pt1 (getpoint "\nPrimeiro ponto do diamtamento...: ")
	pt2 (getpoint pt1 "Segundo ponto do diamtamento... ")
	diam_dist (distance pt1 pt2)
  )
  (cond
    ((= cn7_dwgunit 1.0) (setq new_dist (* diam_dist 100.0)))
    ((= cn7_dwgunit 100.0) (setq new_dist (* diam_dist 1.0)))
    ((= cn7_dwgunit 1000.0) (setq new_dist (* diam_dist 0.1)))
  )
  (if new_dist
    (progn
      (setq jnl_var_diam (rtos new_dist 2 2))
      (jnl_last_writefile)
    )
  )
  (jnl_main)
)

;clica em dois pontos = nova largura
(defun jnl_getlarg_button ()
  (jnl_last_writefile)
  (setq larg_dist nil
	pt1 (getpoint "\nPrimeiro ponto do largtamento...: ")
	pt2 (getpoint pt1 "Segundo ponto do largtamento... ")
	larg_dist (distance pt1 pt2)
  )
  (cond
    ((= cn7_dwgunit 1.0) (setq new_dist (* larg_dist 100.0)))
    ((= cn7_dwgunit 100.0) (setq new_dist (* larg_dist 1.0)))
    ((= cn7_dwgunit 1000.0) (setq new_dist (* larg_dist 0.1)))
  )
  (if new_dist
    (progn
      (setq jnl_var_larg (rtos new_dist 2 2))
      (jnl_last_writefile)
    )
  )
  (jnl_main)
)

;verifica se o valor entrado é válido para vão livre
(defun jnl_getlarg_editaction ()
  (setq jnl_var_newlarg $value)
  (if (distof jnl_var_newlarg)
    (setq jnl_var_larg jnl_var_newlarg)
    (progn
      (alert "Valor Inválido!")
      (set_tile "jnl_getlarg_edit" jnl_var_larg)
      (mode_tile "jnl_getlarg_edit" 2)
    )
  )
)  

;ao clicar no botão "ok"
(defun jnl_ok_action ()
  (jnl_last_writefile)
  (cond
    ((= jnl_var_tipo "11") (jnl_drw11))
    ((= jnl_var_tipo "12") (jnl_drw12))
    ((= jnl_var_tipo "13") (jnl_drw13))
    ((= jnl_var_tipo "14") (jnl_drw14))
    ((= jnl_var_tipo "21") (jnl_drw21))
    ((= jnl_var_tipo "22") (jnl_drw22))
    ((= jnl_var_tipo "23") (jnl_drw23))
    ((= jnl_var_tipo "24") (jnl_drw24))
    ((= jnl_var_tipo "31") (jnl_drw31))
    ((= jnl_var_tipo "32") (jnl_drw32))
    ((= jnl_var_tipo "33") (jnl_drw33))
    ((= jnl_var_tipo "34") (jnl_drw34))
    ((= jnl_var_tipo "41") (jnl_drw41))
    ((= jnl_var_tipo "42") (jnl_drw42))
    ((= jnl_var_tipo "43") (jnl_drw43))
    ((= jnl_var_tipo "44") (jnl_drw44))
  )
  (if (= jnl_var_iden "1")
    (jnl_identify)
  )
)

;atualiza os slides dos tipos de janelas;
(defun jnl_update_slides ()
  ;atualiza as imagens
  (setq x (dimx_tile "icon11")
	y (dimy_tile "icon11"))
  (start_image "icon11")
  (slide_image 0 0 x y (strcat cnp_root "/slides/jnl_11.sld"))
  (end_image)
  (setq x (dimx_tile "icon12")
	y (dimy_tile "icon12"))
  (start_image "icon12")
  (slide_image 0 0 x y (strcat cnp_root "/slides/jnl_12.sld"))
  (end_image)
  (setq x (dimx_tile "icon13")
	y (dimy_tile "icon13"))
  (start_image "icon13")
  (slide_image 0 0 x y (strcat cnp_root "/slides/jnl_13.sld"))
  (end_image)
  (setq x (dimx_tile "icon14")
	y (dimy_tile "icon14"))
  (start_image "icon14")
  (slide_image 0 0 x y (strcat cnp_root "/slides/jnl_14.sld"))
  (end_image)
  (setq x (dimx_tile "icon21")
	y (dimy_tile "icon21"))
  (start_image "icon21")
  (slide_image 0 0 x y (strcat cnp_root "/slides/jnl_21.sld"))
  (end_image)
  (setq x (dimx_tile "icon22")
	y (dimy_tile "icon22"))
  (start_image "icon22")
  (slide_image 0 0 x y (strcat cnp_root "/slides/jnl_22.sld"))
  (end_image)
  (setq x (dimx_tile "icon23")
	y (dimy_tile "icon23"))
  (start_image "icon23")
  (slide_image 0 0 x y (strcat cnp_root "/slides/jnl_23.sld"))
  (end_image)
  (setq x (dimx_tile "icon24")
	y (dimy_tile "icon24"))
  (start_image "icon24")
  (slide_image 0 0 x y (strcat cnp_root "/slides/jnl_24.sld"))
  (end_image)
  (setq x (dimx_tile "icon31")
	y (dimy_tile "icon31"))
  (start_image "icon31")
  (slide_image 0 0 x y (strcat cnp_root "/slides/jnl_31.sld"))
  (end_image)
  (setq x (dimx_tile "icon32")
	y (dimy_tile "icon32"))
  (start_image "icon32")
  (slide_image 0 0 x y (strcat cnp_root "/slides/jnl_32.sld"))
  (end_image)
  (setq x (dimx_tile "icon33")
	y (dimy_tile "icon33"))
  (start_image "icon33")
  (slide_image 0 0 x y (strcat cnp_root "/slides/jnl_33.sld"))
  (end_image)
  (setq x (dimx_tile "icon34")
	y (dimy_tile "icon34"))
  (start_image "icon34")
  (slide_image 0 0 x y (strcat cnp_root "/slides/jnl_34.sld"))
  (end_image)
  (setq x (dimx_tile "icon41")
	y (dimy_tile "icon41"))
  (start_image "icon41")
  (slide_image 0 0 x y (strcat cnp_root "/slides/jnl_41.sld"))
  (end_image)
  (setq x (dimx_tile "icon42")
	y (dimy_tile "icon42"))
  (start_image "icon42")
  (slide_image 0 0 x y (strcat cnp_root "/slides/jnl_42.sld"))
  (end_image)
  (setq x (dimx_tile "icon43")
	y (dimy_tile "icon43"))
  (start_image "icon43")
  (slide_image 0 0 x y (strcat cnp_root "/slides/jnl_43.sld"))
  (end_image)
  (setq x (dimx_tile "icon44")
	y (dimy_tile "icon44"))
  (start_image "icon44")
  (slide_image 0 0 x y (strcat cnp_root "/slides/jnl_44.sld"))
  (end_image)
  (action_tile "icon11" "(jnl_deftype)")
  (action_tile "icon12" "(jnl_deftype)")
  (action_tile "icon13" "(jnl_deftype)")
  (action_tile "icon14" "(jnl_deftype)")
  (action_tile "icon21" "(jnl_deftype)")
  (action_tile "icon22" "(jnl_deftype)")
  (action_tile "icon23" "(jnl_deftype)")
  (action_tile "icon24" "(jnl_deftype)")
  (action_tile "icon31" "(jnl_deftype)")
  (action_tile "icon32" "(jnl_deftype)")
  (action_tile "icon33" "(jnl_deftype)")
  (action_tile "icon34" "(jnl_deftype)")
  (action_tile "icon41" "(jnl_deftype)")
  (action_tile "icon42" "(jnl_deftype)")
  (action_tile "icon43" "(jnl_deftype)")
  (action_tile "icon44" "(jnl_deftype)")
)


;ação ao escolher o typo de porta
(defun jnl_deftype ()
  ;determina o tipo
  (setq jnl_var_type $key
	jnl_var_tipo (substr jnl_var_type 5 2)
	x (dimx_tile "jnl_slide_type")
	y (dimy_tile "jnl_slide_type")
  )
  ;atualiza o slide
  (start_image "jnl_slide_type")
  (fill_image 0 0 x y -2)
  (slide_image 0 0 x y (strcat cnp_root "/slides/jnl_" jnl_var_tipo ".sld"))
  (end_image)
  ;avalia o botão ~Detalhes do Tipo"
)

;lê os dados iniciais da DCL no arquivo de dados
(defun jnl_last_file ()
  (if (findfile (strcat cnp_root "/config/jnl_last.txt"))
    (jnl_last_readfile)
    (progn
      (setq file (open (strcat cnp_root "/config/jnl_last.txt") "w" "utf8"))
      (write-line "11" file)
      (write-line "120" file)
      (write-line "0" file)
      (write-line "jnl_center" file)
      (write-line "5" file)
      (write-line "15" file)
      (write-line "2" file)
      (write-line "1" file)
      (write-line "jnl_larg_radio1" file)
      (write-line "80" file)
      (close file)
      (jnl_last_readfile)
    )
  )
)

;função que lê o arquivo de dados
(defun jnl_last_readfile ()
  (setq	file (open (strcat cnp_root "/config/jnl_last.txt") "r" "utf8"))
  (setq	jnl_var_tipo (read-line file))
  (setq	jnl_var_larg (read-line file))
  (setq	jnl_var_halt (read-line file))
  (setq	jnl_var_posi (read-line file))
  (setq	jnl_var_afas (read-line file))
  (setq	jnl_var_wall (read-line file))
  (setq	jnl_var_caix (read-line file))
  (setq	jnl_var_iden (read-line file))
  (setq	jnl_var_lrad (read-line file))
  (setq	jnl_var_diam (read-line file))
  (close file)
)

;função que escreve o arquivo de dados
(defun jnl_last_writefile ()
  (setq	file (open (strcat cnp_root "/config/jnl_last.txt") "w" "utf8"))
  (write-line jnl_var_tipo file)
  (write-line jnl_var_larg file)
  (write-line jnl_var_halt file)
  (write-line jnl_var_posi file)
  (write-line jnl_var_afas file)
  (write-line jnl_var_wall file)
  (write-line jnl_var_caix file)
  (write-line jnl_var_iden file)
  (write-line jnl_var_lrad file)
  (write-line jnl_var_diam file)
  (close file)
)


;****************************
;Janela tipo 11              
;****************************
(defun jnl_drw11 ()
  (setq jnl_visible 1)
  (jnl_start)
  (jnl_openfree_break)
  ;desenha o caixilho, se houver
  (jnl_draw_caixilho)
  (jnl_draw_parapeito)
  (jnl_draw_vidro_mduplo)
  (devolve)
  (prompt "\nUse o comando <UB> para retornar... ")
)

;****************************
;Janela tipo 12              
;****************************
(defun jnl_drw12 ()
  (setq jnl_visible 1)
  (jnl_start)
  (jnl_openfree_break)
  ;desenha o caixilho, se houver
  (jnl_draw_caixilho)
  (jnl_draw_parapeito)
  (jnl_draw_vidro_msimples)
  (devolve)
  (prompt "\nUse o comando <UB> para retornar... ")
)

;****************************
;Janela tipo 13              
;****************************
(defun jnl_drw13 ()
  (setq jnl_visible 1)
  (jnl_start)
  (jnl_openfree_break)
  ;desenha o caixilho, se houver
  (jnl_draw_caixilho)
  (jnl_draw_parapeito_1)
  (jnl_draw_vidro_cduplo)
  (devolve)
  (prompt "\nUse o comando <UB> para retornar... ")
)

;****************************
;Janela tipo 14              
;****************************
(defun jnl_drw14 ()
  (setq jnl_visible 1)
  (jnl_start)
  (jnl_openfree_break)
  ;desenha o caixilho, se houver
  (jnl_draw_caixilho)
  (jnl_draw_parapeito_1)
  (jnl_draw_vidro_csimples)
  (devolve)
  (prompt "\nUse o comando <UB> para retornar... ")
)

;****************************
;Janela tipo 21              
;****************************
(defun jnl_drw21 ()
  (setq jnl_visible 0)
  (jnl_start)
  ;desenha o caixilho, se houver
  (jnl_draw_caixilho)
  (jnl_draw_vidro_mduplo)
  (devolve)
  (prompt "\nUse o comando <UB> para retornar... ")
)

;****************************
;Janela tipo 22              
;****************************
(defun jnl_drw22 ()
  (setq jnl_visible 0)
  (jnl_start)
  ;desenha o caixilho, se houver
  (jnl_draw_caixilho)
  (jnl_draw_vidro_msimples)
  (devolve)
  (prompt "\nUse o comando <UB> para retornar... ")
)

;****************************
;Janela tipo 23              
;****************************
(defun jnl_drw23 ()
  (setq jnl_visible 0)
  (jnl_start)
  ;desenha o caixilho, se houver
  (jnl_draw_caixilho)
  (jnl_draw_vidro_cduplo)
  (devolve)
  (prompt "\nUse o comando <UB> para retornar... ")
)

;****************************
;Janela tipo 24              
;****************************
(defun jnl_drw24 ()
  (setq jnl_visible 0)
  (jnl_start)
  ;desenha o caixilho, se houver
  (jnl_draw_caixilho)
  (devolve)
  (prompt "\nUse o comando <UB> para retornar... ")
)

;****************************
;Janela tipo 31              
;****************************
(defun jnl_drw31 ()
  (if (not jnl_var_qtd) (setq jnl_var_qtd "2"))
  (jnl_getqtd)
  (setq jnl_visible 1)
  (jnl_start)
  (jnl_openfree_break)
  ;desenha o caixilho, se houver
  (jnl_draw_caixilho)
  (jnl_draw_parapeito)
  (jnl_draw_multdef_1)
  (jnl_multi_duplo_middle)
  (repeat (1- (fix (distof jnl_var_qtd)))
    (setq jnl_va jnl_vb
	  jnl_vb (polar jnl_vb jnl_angbase jnl_vao)
    )
    (jnl_multi_duplo_middle)
  )
  (devolve)
  (prompt "\nUse o comando <UB> para retornar... ")
)

;****************************
;Janela tipo 32              
;****************************
(defun jnl_drw32 ()
  (if (not jnl_var_qtd) (setq jnl_var_qtd "2"))
  (jnl_getqtd)
  (setq jnl_visible 1)
  (jnl_start)
  (jnl_openfree_break)
  ;desenha o caixilho, se houver
  (jnl_draw_caixilho)
  (jnl_draw_parapeito)
  (jnl_draw_multdef_1)
  (jnl_multi_simples_middle)
  (repeat (1- (fix (distof jnl_var_qtd)))
    (setq jnl_va jnl_vb
	  jnl_vb (polar jnl_vb jnl_angbase jnl_vao)
    )
    (jnl_multi_simples_middle)
  )
  (devolve)
  (prompt "\nUse o comando <UB> para retornar... ")
)

;****************************
;Janela tipo 33              
;****************************
(defun jnl_drw33 ()
  (if (not jnl_var_qtd) (setq jnl_var_qtd "2"))
  (jnl_getqtd)
  (setq jnl_visible 1)
  (jnl_start)
  (jnl_openfree_break)
  ;desenha o caixilho, se houver
  (jnl_draw_caixilho)
  (jnl_draw_parapeito_1)
  (jnl_test_visible)
  (command "._line" "_non" jnl_cxi3 "_non" jnl_cxi4 "")
  (jnl_draw_multdef_2)
  (jnl_multi_duplo_corner)
  (repeat (1- (fix (distof jnl_var_qtd)))
    (setq jnl_va jnl_vb
	  jnl_vb (polar jnl_vb jnl_angbase jnl_vao)
    )
    (jnl_multi_duplo_corner)
  )
  (devolve)
  (prompt "\nUse o comando <UB> para retornar... ")
)


;****************************
;Janela tipo 34              
;****************************
(defun jnl_drw34 ()
  (if (not jnl_var_qtd) (setq jnl_var_qtd "2"))
  (jnl_getqtd)
  (setq jnl_visible 1)
  (jnl_start)
  (jnl_openfree_break)
  ;desenha o caixilho, se houver
  (jnl_draw_caixilho)
  (jnl_draw_parapeito_1)
  (jnl_test_visible)
  (command "._line" "_non" jnl_cxi3 "_non" jnl_cxi4 "")
  (jnl_draw_multdef_2)
  (jnl_multi_simples_corner)
  (repeat (1- (fix (distof jnl_var_qtd)))
    (setq jnl_va jnl_vb
	  jnl_vb (polar jnl_vb jnl_angbase jnl_vao)
    )
    (jnl_multi_simples_corner)
  )
  (devolve)
  (prompt "\nUse o comando <UB> para retornar... ")
)

;****************************
;Janela tipo 41              
;****************************
(defun jnl_drw41 ()
  (if (not jnl_var_qtd) (setq jnl_var_qtd "2"))
  (jnl_getqtd)
  (setq jnl_visible 0)
  (jnl_start)
  ;desenha o caixilho, se houver
  (jnl_draw_caixilho)
  (jnl_draw_multdef_1)
  (jnl_multi_duplo_middle)
  (repeat (1- (fix (distof jnl_var_qtd)))
    (setq jnl_va jnl_vb
	  jnl_vb (polar jnl_vb jnl_angbase jnl_vao)
    )
    (jnl_multi_duplo_middle)
  )
  (devolve)
  (prompt "\nUse o comando <UB> para retornar... ")
)

;****************************
;Janela tipo 42              
;****************************
(defun jnl_drw42 ()
  (if (not jnl_var_qtd) (setq jnl_var_qtd "2"))
  (jnl_getqtd)
  (setq jnl_visible 0)
  (jnl_start)
  ;desenha o caixilho, se houver
  (jnl_draw_caixilho)
  (jnl_draw_multdef_1)
  (jnl_multi_simples_middle)
  (repeat (1- (fix (distof jnl_var_qtd)))
    (setq jnl_va jnl_vb
	  jnl_vb (polar jnl_vb jnl_angbase jnl_vao)
    )
    (jnl_multi_simples_middle)
  )
  (devolve)
  (prompt "\nUse o comando <UB> para retornar... ")
)


;****************************
;Janela tipo 43              
;****************************
(defun jnl_drw43 ()
  (if (not jnl_var_qtd) (setq jnl_var_qtd "2"))
  (jnl_getqtd)
  (setq jnl_visible 0)
  (jnl_start)
  ;desenha o caixilho, se houver
  (jnl_draw_caixilho)
  (jnl_draw_multdef_2)
  (jnl_multi_duplo_corner)
  (repeat (1- (fix (distof jnl_var_qtd)))
    (setq jnl_va jnl_vb
	  jnl_vb (polar jnl_vb jnl_angbase jnl_vao)
    )
    (jnl_multi_duplo_corner)
  )
  (devolve)
  (prompt "\nUse o comando <UB> para retornar... ")
)

;****************************
;Janela tipo 44 - cobogó     
;****************************
(defun jnl_drw44 ()
  (jnl_cobo_file)
  (setq dcl_id (load_dialog (strcat cnp_root "/lisp/cadnorma.dcl")))
  (if (not (new_dialog "jnl_cobo" dcl_id)) (exit))
  ;largura do vão (abertura)
  (set_tile  "jnl_cobo_vao" jnl_cobo_vao)
  (action_tile "jnl_cobo_vao" "(jnl_cobo_getvao)")
  (action_tile "jnl_cobo_pick" "(done_dialog 2)")
  ;avalia as opções do radio
  (set_tile "jnl_cobo_radio" jnl_cobo_def)
  (set_tile "jnl_cobo_qtd" jnl_cobo_qtd)
  (action_tile "jnl_cobo_qtd" "(jnl_cobo_getqtd)")
  (set_tile "jnl_cobo_pct" jnl_cobo_pct)
  (action_tile "jnl_cobo_pct" "(jnl_cobo_getpct)")
  (jnl_cobo_radioaction2)
  (action_tile "jnl_cobo_radio" "(jnl_cobo_radioaction)")
  ;visibilidade
  (set_tile "jnl_cobo_visib" jnl_cobo_vis)
  (action_tile "jnl_cobo_visib" "(setq jnl_cobo_vis $value)")
  ;ações ok_cancel
  (action_tile "cancel" "(done_dialog 0)")
  (action_tile "accept" "(done_dialog 1)")
  (setq jnl_cobo_id (start_dialog))
  (unload_dialog dcl_id)
  (if (= 0 jnl_cobo_id) (exit))
  (if (= 1 jnl_cobo_id) (jnl_cobo_ok))
  (if (= 2 jnl_cobo_id) (jnl_cobo_pickvao))
)

;ao clicar em ok
(defun jnl_cobo_ok ()
  (setq jnl_caix 0.0 jnl_var_caix "0.0")
  (jnl_cobo_writefile)
  (jnl_last_writefile)
  (jnl_start)
  (jnl_last_file)
  (if (= jnl_cobo_vis "jnl_cobo_vista")
    (progn
      (setq jnl_visible 1)
      (jnl_openfree_break)
      (jnl_cobo_drwvis)
    )
    (progn
      (setq jnl_visible 0)
      (jnl_cobo_drwprj)
    )
  )
)

;desenho em projeção
(defun jnl_cobo_drwprj ()
  (if (= jnl_cobo_def "jnl_cobo_radio1")
    (setq jnl_cobo_truqtd (distof jnl_cobo_qtd))
    (setq jnl_cobo_truqtd jnl_cobo_res_qtd)
  )
  (setq jnl_cobo_truesp (* jnl_fator jnl_cobo_res_esp)
	jnl_cobo_truvao (* jnl_fator (distof jnl_cobo_vao))
        jnl_cobo_pt1 jnl_brk1
	jnl_cobo_pt4 jnl_brk3
	jnl_cobo_end1 jnl_brk2
	jnl_cobo_end2 jnl_brk4
  )
  (jnl_test_visible)
  (command "._line" "_non" jnl_brk1 "_non" jnl_brk3 "" "._chprop" (entlast) "" "_s" 0.5 "")
  (command "._line" "_non" jnl_brk2 "_non" jnl_brk4 "" "._chprop" (entlast) "" "_s" 0.5 "")
  (repeat (1- (fix jnl_cobo_truqtd))
    (setq jnl_cobo_pt2 (polar jnl_cobo_pt1 jnl_angbase jnl_cobo_truvao)
	  jnl_cobo_pt3 (polar jnl_cobo_pt2 jnl_angbase jnl_cobo_truesp)
	  jnl_cobo_pt5 (polar jnl_cobo_pt4 jnl_angbase jnl_cobo_truvao)
	  jnl_cobo_pt6 (polar jnl_cobo_pt5 jnl_angbase jnl_cobo_truesp)
    )
    (command "._line" "_non" jnl_cobo_pt2 "_non" jnl_cobo_pt5 "" "._chprop" (entlast) "" "_s" 0.5 "")
    (command "._line" "_non" jnl_cobo_pt3 "_non" jnl_cobo_pt6 "" "._chprop" (entlast) "" "_s" 0.5 "")
    (command "._line" "_non" jnl_cobo_pt1 "_non" jnl_cobo_pt5 "" "._chprop" (entlast) "" "_s" 0.5 "")
    (command "._line" "_non" jnl_cobo_pt4 "_non" jnl_cobo_pt2 "" "._chprop" (entlast) "" "_s" 0.5 "")
    (setq jnl_cobo_pt1 jnl_cobo_pt3
	  jnl_cobo_pt4 jnl_cobo_pt6
    )
  )
  (command "._line" "_non" jnl_cobo_pt6 "_non" jnl_brk2 "" "._chprop" (entlast) "" "_s" 0.5 "")
  (command "._line" "_non" jnl_cobo_pt3 "_non" jnl_brk4 "" "._chprop" (entlast) "" "_s" 0.5 "")
)

;desenho em vista
(defun jnl_cobo_drwvis ()
  (if (= jnl_cobo_def "jnl_cobo_radio1")
    (setq jnl_cobo_truqtd (distof jnl_cobo_qtd))
    (setq jnl_cobo_truqtd jnl_cobo_res_qtd)
  )
  (setq jnl_cobo_truesp (* jnl_fator jnl_cobo_res_esp)
	jnl_cobo_truvao (* jnl_fator (distof jnl_cobo_vao))
        jnl_cobo_pt1 jnl_brk1
	jnl_cobo_pt4 jnl_brk3
	jnl_cobo_end1 jnl_brk2
	jnl_cobo_end2 jnl_brk4
  )
  (repeat (1- (fix jnl_cobo_truqtd))
    (setq jnl_cobo_pt2 (polar jnl_cobo_pt1 jnl_angbase jnl_cobo_truvao)
	  jnl_cobo_pt3 (polar jnl_cobo_pt2 jnl_angbase jnl_cobo_truesp)
	  jnl_cobo_pt5 (polar jnl_cobo_pt4 jnl_angbase jnl_cobo_truvao)
	  jnl_cobo_pt6 (polar jnl_cobo_pt5 jnl_angbase jnl_cobo_truesp)
    )
    (command "._layer" "_s" jnl_wall_layer "")
    (setvar "celtype" "bylayer")
    (setvar "cecolor" "bylayer")
    (command "._line" "_non" jnl_cobo_pt2 "_non" jnl_cobo_pt3 "_non" jnl_cobo_pt6 "_non" jnl_cobo_pt5 "_c")
    (cn7_verylayer jnl_layc_ppl 7)
    (setvar "cecolor" jnl_layc_ppc)
    (setvar "celtype" "bylayer")
    (command "._line" "_non" jnl_cobo_pt1 "_non" jnl_cobo_pt2 "")
    (command "._line" "_non" jnl_cobo_pt4 "_non" jnl_cobo_pt5 "")
    (setq jnl_cobo_pt1 jnl_cobo_pt3
	  jnl_cobo_pt4 jnl_cobo_pt6
    )
  )
  (command "._line" "_non" jnl_cobo_pt3 "_non" jnl_brk2 "")
  (command "._line" "_non" jnl_cobo_pt6 "_non" jnl_brk4 "")
)

;ao clicar em um botão de rádio
(defun jnl_cobo_radioaction ()
  (setq jnl_cobo_def $value)
  (jnl_cobo_radioaction2)
)

(defun jnl_cobo_radioaction2 ()
  (cond
    ((= jnl_cobo_def "jnl_cobo_radio1")
     (mode_tile "jnl_cobo_qtd" 0)
     (mode_tile "jnl_cobo_pct" 1)
     (set_tile "jnl_cobo_tx2" "% Livre:")
     (jnl_cobo_calc1)
     (set_tile "jnl_cobo_tx3" (strcat (rtos jnl_cobo_res_esp 2 1) "cm"))
     (set_tile "jnl_cobo_tx4" (strcat (rtos jnl_cobo_res_pct 2 1) "%"))
    )
    ((= jnl_cobo_def "jnl_cobo_radio2")
     (mode_tile "jnl_cobo_qtd" 1)
     (mode_tile "jnl_cobo_pct" 0)
     (set_tile "jnl_cobo_tx2" "Quant. Espaços:")
     (jnl_cobo_calc2)
     (set_tile "jnl_cobo_tx3" (strcat (rtos jnl_cobo_res_esp 2 1) "cm"))
     (set_tile "jnl_cobo_tx4" (rtos jnl_cobo_res_qtd 2 0))
    )
   )
)


;cálculo dando a espessura
(defun jnl_cobo_calc2 ()
  (setq jnl_cobo_res_fre (/ (* (distof jnl_var_larg) (distof jnl_cobo_pct)) 100.0)
	jnl_cobo_res_qtd (1+ (fix (/ jnl_cobo_res_fre (distof jnl_cobo_vao))))
	jnl_cobo_res_fre (* jnl_cobo_res_qtd (distof jnl_cobo_vao))
	jnl_cobo_res_esp (/ (- (distof jnl_var_larg) jnl_cobo_res_fre) (1- jnl_cobo_res_qtd))
  )  
)

;cálculo dando a quantidade de aberturas
(defun jnl_cobo_calc1 ()
  ;avalia o espaço livre necessário
  (setq jnl_cobo_res_fre (* (distof jnl_cobo_vao) (distof jnl_cobo_qtd)))
  (if (>= jnl_cobo_res_fre (distof jnl_var_larg))
    (progn
      (alert "Valor excede a largura disponível!\nReduza a abertura ou a quant. espaços.")
    )
    (progn
      (setq jnl_cobo_res_pct (* 100.0 (/ jnl_cobo_res_fre (distof jnl_var_larg)))
	    jnl_cobo_res_esp (/ (- (distof jnl_var_larg) jnl_cobo_res_fre) (1- (distof jnl_cobo_qtd)))
	    jnl_cobo_res_qtd (distof jnl_cobo_qtd)
      )
    )
  )
)

;clica em dois pontos = nova abertura
(defun jnl_cobo_pickvao ()
  (setq vao_dist nil
	pt1 (getpoint "\nPrimeiro ponto...: ")
	pt2 (getpoint pt1 "Segundo ponto... ")
	vao_dist (distance pt1 pt2)
  )
  (cond
    ((= cn7_dwgunit 1.0) (setq new_dist (* vao_dist 100.0)))
    ((= cn7_dwgunit 100.0) (setq new_dist (* vao_dist 1.0)))
    ((= cn7_dwgunit 1000.0) (setq new_dist (* vao_dist 0.1)))
  )
  (if new_dist
    (progn
      (setq jnl_cobo_vao (rtos new_dist 2 2))
      (jnl_cobo_writefile)
    )
  )
  (jnl_drw44)
)

;verifica se o valor entrado é válido
(defun jnl_cobo_getpct ()
  (setq jnl_cobo_newpct $value)
  (if (distof jnl_cobo_newpct)
    (progn
      (setq jnl_cobo_pct jnl_cobo_newpct)
      (jnl_cobo_radioaction2)
    )
    (progn
      (alert "Valor Inválido!\nDigite um número real.")
      (set_tile "jnl_cobo_pct" jnl_cobo_pct)
      (mode_tile "jnl_cobo_pct" 2)
    )
  )
)

;verifica se o valor entrado é válido
(defun jnl_cobo_getqtd ()
  (setq jnl_cobo_newqtd $value)
  (if (and (distof jnl_cobo_newqtd) (= (distof jnl_cobo_newqtd) (fix (distof jnl_cobo_newqtd))))
    (progn
      (setq jnl_cobo_qtd jnl_cobo_newqtd)
      (jnl_cobo_radioaction2)
    )
    (progn
      (alert "Valor Inválido!\nDigite um número inteiro.")
      (set_tile "jnl_cobo_qtd" jnl_cobo_qtd)
      (mode_tile "jnl_cobo_qtd" 2)
    )
  )
)

;verifica se o valor entrado é válido
(defun jnl_cobo_getvao ()
  (setq jnl_cobo_newvao $value)
  (if (distof jnl_cobo_newvao)
    (progn
      (setq jnl_cobo_vao jnl_cobo_newvao)
      (jnl_cobo_radioaction2)
    )
    (progn
      (alert "Valor Inválido!\nDigite um número real.")
      (set_tile "jnl_cobo_vao" jnl_cobo_vao)
      (mode_tile "jnl_cobo_vao" 2)
    )
  )
)

;lê os dados iniciais da DCL no arquivo de dados
(defun jnl_cobo_file ()
  (if (findfile (strcat cnp_root "/config/jnl_cobo.txt"))
    (jnl_cobo_readfile)
    (progn
      (setq file (open (strcat cnp_root "/config/jnl_cobo.txt") "w" "utf8"))
      (write-line "10" file)
      (write-line "jnl_cobo_radio1" file)
      (write-line "10" file)
      (write-line "50" file)
      (write-line "jnl_cobo_vista" file)
      (close file)
      (jnl_cobo_readfile)
    )
  )
)

;função que lê o arquivo de dados
(defun jnl_cobo_readfile ()
  (setq	file (open (strcat cnp_root "/config/jnl_cobo.txt") "r" "utf8"))
  (setq	jnl_cobo_vao (read-line file))
  (setq	jnl_cobo_def (read-line file))
  (setq	jnl_cobo_qtd (read-line file))
  (setq	jnl_cobo_pct (read-line file))
  (setq	jnl_cobo_vis (read-line file))
  (close file)
)

;função que escreve o arquivo de dados
(defun jnl_cobo_writefile ()
  (setq	file (open (strcat cnp_root "/config/jnl_cobo.txt") "w" "utf8"))
  (write-line jnl_cobo_vao file)
  (write-line jnl_cobo_def file)
  (write-line jnl_cobo_qtd file)
  (write-line jnl_cobo_pct file)
  (write-line jnl_cobo_vis file)
  (close file)
)

;**********************************************
;Desenhos dos vidros  e janelas multi-vãos     
;**********************************************

;Multi-janelas simples, no canto
(defun jnl_multi_simples_corner ()
  (setq jnl_mv1 (polar jnl_va (+ jnl_angortho pi) (* jnl_fator 5.0))	
	jnl_mv2 (polar jnl_mv1 jnl_angbase (* jnl_fator 2.0))	
	jnl_mv3 (polar jnl_mv2 jnl_angortho (* jnl_fator 5.0))	
	jnl_mv4 (polar jnl_vb (+ jnl_angortho pi) (* jnl_fator 5.0))
	jnl_mv5 (polar jnl_mv4 (+ jnl_angbase pi) (* jnl_fator 2.0))	
	jnl_mv6 (polar jnl_mv5 jnl_angortho (* jnl_fator 5.0))	

  )
  (jnl_test_visible)
  (command "._line" "_non" jnl_mv1 "_non" jnl_mv2  "_non" jnl_mv3 "")
  (command "._line" "_non" jnl_mv4 "_non" jnl_mv5  "_non" jnl_mv6 "")
)

;Multi-janelas duplas, no canto
(defun jnl_multi_duplo_corner ()
  (setq jnl_mv1 (polar jnl_va (+ jnl_angortho pi) (* jnl_fator 5.0))	
	jnl_mv2 (polar jnl_mv1 jnl_angbase (* jnl_fator 2.0))	
	jnl_mv3 (polar jnl_mv2 jnl_angortho (* jnl_fator 5.0))	
	jnl_mv4 (polar jnl_vb (+ jnl_angortho pi) (* jnl_fator 5.0))
	jnl_mv5 (polar jnl_mv4 (+ jnl_angbase pi) (* jnl_fator 2.0))	
	jnl_mv6 (polar jnl_mv5 jnl_angortho (* jnl_fator 5.0))	
	jnl_mv7 (polar jnl_mv3 (+ jnl_angortho pi) (* jnl_fator 3.0))
	jnl_mv8 (polar jnl_mv6 (+ jnl_angortho pi) (* jnl_fator 3.0))
  )
  (jnl_test_visible)
  (command "._line" "_non" jnl_mv1 "_non" jnl_mv2  "_non" jnl_mv3 "")
  (command "._line" "_non" jnl_mv4 "_non" jnl_mv5  "_non" jnl_mv6 "")
  (command "._line" "_non" jnl_mv7 "_non" jnl_mv8 "")
)


;Multi-janelas simples no centro
(defun jnl_multi_simples_middle ()
  (setq jnl_mv1 (polar jnl_va (+ jnl_angortho pi) (* jnl_fator 2.5))
	jnl_mv2 (polar jnl_mv1 jnl_angbase (* jnl_fator 2.0))
	jnl_mv3 (polar jnl_mv2 jnl_angortho (* jnl_fator 5.0))
	jnl_mv4 (polar jnl_mv3 (+ jnl_angbase pi) (* jnl_fator 2.0))
	jnl_mv5 (polar jnl_vb (+ jnl_angortho pi) (* jnl_fator 2.5))
	jnl_mv6 (polar jnl_mv5 (+ jnl_angbase pi) (* jnl_fator 2.0))
	jnl_mv7 (polar jnl_mv6 jnl_angortho (* jnl_fator 5.0))
	jnl_mv8 (polar jnl_mv7 jnl_angbase (* jnl_fator 2.0))
	jnl_ma1 (polar jnl_va jnl_angbase (* jnl_fator 2.0))
	jnl_mb1 (polar jnl_vb (+ jnl_angbase pi) (* jnl_fator 2.0))
  )
  (jnl_test_visible)
  (command "._line" "_non" jnl_mv1 "_non" jnl_mv2  "_non" jnl_mv3  "_non" jnl_mv4 "")
  (command "._line" "_non" jnl_mv5 "_non" jnl_mv6  "_non" jnl_mv7  "_non" jnl_mv8 "")
  (command "._line" "_non" jnl_ma1 "_non" jnl_mb1 "")
)

;Multi-janelas duplas, no centro
(defun jnl_multi_duplo_middle ()
  (setq jnl_mv1 (polar jnl_va (+ jnl_angortho pi) (* jnl_fator 2.5))
	jnl_mv2 (polar jnl_mv1 jnl_angbase (* jnl_fator 2.0))
	jnl_mv3 (polar jnl_mv2 jnl_angortho (* jnl_fator 5.0))
	jnl_mv4 (polar jnl_mv3 (+ jnl_angbase pi) (* jnl_fator 2.0))
	jnl_mv5 (polar jnl_vb (+ jnl_angortho pi) (* jnl_fator 2.5))
	jnl_mv6 (polar jnl_mv5 (+ jnl_angbase pi) (* jnl_fator 2.0))
	jnl_mv7 (polar jnl_mv6 jnl_angortho (* jnl_fator 5.0))
	jnl_mv8 (polar jnl_mv7 jnl_angbase (* jnl_fator 2.0))
	jnl_ma1 (polar jnl_va jnl_angbase (* jnl_fator 2.0))
	jnl_mb1 (polar jnl_vb (+ jnl_angbase pi) (* jnl_fator 2.0))
	jnl_mv9 (polar jnl_ma1 (+ jnl_angortho pi) (* jnl_fator 1.5))
	jnl_mv10 (polar jnl_mb1 (+ jnl_angortho pi) (* jnl_fator 1.5))
	jnl_mv11 (polar jnl_mv9 jnl_angortho (* jnl_fator 3.0))
	jnl_mv12 (polar jnl_mv10 jnl_angortho (* jnl_fator 3.0))
  )
  (jnl_test_visible)
  (command "._line" "_non" jnl_mv1 "_non" jnl_mv2  "_non" jnl_mv3  "_non" jnl_mv4 "")
  (command "._line" "_non" jnl_mv5 "_non" jnl_mv6  "_non" jnl_mv7  "_non" jnl_mv8 "")
  (command "._line" "_non" jnl_mv9 "_non" jnl_mv10 "")
  (command "._line" "_non" jnl_mv11 "_non" jnl_mv12 "")
)

;*************************
;Multi-vãos - Definições  
;*************************

;no centro
(defun jnl_draw_multdef_1 ()
  (setq jnl_vao (/ jnl_larg (fix (distof jnl_var_qtd)))
	jnl_va (polar jnl_cxi1 jnl_angortho (/ jnl_wall 2.0))
	jnl_vb (polar jnl_va jnl_angbase jnl_vao)
  )
)

;no canto
(defun jnl_draw_multdef_2 ()
  (setq jnl_vao (/ jnl_larg (fix (distof jnl_var_qtd)))
	jnl_va jnl_cxi3
	jnl_vb (polar jnl_va jnl_angbase jnl_vao)
  )
)

;coleta o número de vãos
(defun jnl_getqtd ()
  (setq dcl_id (load_dialog (strcat cnp_root "/lisp/cadnorma.dcl")))
  (if (not (new_dialog "jnl_getqtd" dcl_id)) (exit))
  (set_tile "jnl_getqtd_edit" jnl_var_qtd)
  (action_tile "jnl_getqtd_edit" "(jnl_getqtd_editaction)")
  (mode_tile "jnl_getqtd_edit" 2)
  (setq jnl_getqtd_id (start_dialog))
  (unload_dialog dcl_id)
)

;verifica se o valor entrado é válido
(defun jnl_getqtd_editaction ()
  (setq jnl_var_newqtd $value)
  (if (distof jnl_var_newqtd)
    (setq jnl_var_qtd jnl_var_newqtd)
    (progn
      (alert "Valor Inválido!\nDigite um número inteiro.")
      (set_tile "jnl_getqtd_edit" jnl_var_qtd)
      (mode_tile "jnl_getqtd_edit" 2)
    )
  )
)


;***********************************
;Desenhos dos vidros em vãos únicos 
;***********************************


;Desenho do Vidro Simples, no canto       
(defun jnl_draw_vidro_csimples ()
  (if (= jnl_visible 1)
    (progn
      (cn7_verylayer jnl_layc_vil 7)
      (setvar "cecolor" jnl_layc_vic)
      (command "._line" "_non" jnl_cxi3 "_non" jnl_cxi4 "")
    )
  )
)

;Desenho do Vidro Duplo, no canto         
(defun jnl_draw_vidro_cduplo ()
  (setq jnl_vid1 (polar jnl_cxi3 (+ jnl_angortho pi) (* 3.0 jnl_fator))
	jnl_vid2 (polar jnl_cxi4 (+ jnl_angortho pi) (* 3.0 jnl_fator))
  )
  (jnl_test_visible)
  (if (= jnl_visible 1)
    (command "._line" "_non" jnl_cxi3 "_non" jnl_cxi4 "")
  )
  (command "._line" "_non" jnl_vid1 "_non" jnl_vid2 "")
)

;Desenho do Vidro Simples no meio         
(defun jnl_draw_vidro_msimples ()
  (setq jnl_vid0a (polar jnl_cxi1 (angle jnl_cxi1 jnl_cxi3) (/ (distance jnl_cxi1 jnl_cxi3) 2))
	jnl_vid0b (polar jnl_cxi2 (angle jnl_cxi2 jnl_cxi4) (/ (distance jnl_cxi2 jnl_cxi4) 2))
  )
  (jnl_test_visible)
  (command "._line" "_non" jnl_vid0a "_non" jnl_vid0b "")
)

;Desenho do Vidro Duplo, no meio          
(defun jnl_draw_vidro_mduplo ()
  (setq jnl_vid0a (polar jnl_cxi1 (angle jnl_cxi1 jnl_cxi3) (/ (distance jnl_cxi1 jnl_cxi3) 2))
	jnl_vid0b (polar jnl_cxi2 (angle jnl_cxi2 jnl_cxi4) (/ (distance jnl_cxi2 jnl_cxi4) 2))
	jnl_vid1 (polar jnl_vid0a (+ jnl_angortho pi) (* 1.5 jnl_fator))
	jnl_vid3 (polar jnl_vid0a jnl_angortho (* 1.5 jnl_fator))
	jnl_vid2 (polar jnl_vid0b (+ jnl_angortho pi) (* 1.5 jnl_fator))
	jnl_vid4 (polar jnl_vid0b jnl_angortho (* 1.5 jnl_fator))
  )
  (jnl_test_visible)
  (command "._line" "_non" jnl_vid1 "_non" jnl_vid2 "")
  (command "._line" "_non" jnl_vid3 "_non" jnl_vid4 "")
)


;*****************************************
;Desenho das Parapeito                    
;*****************************************
(defun jnl_draw_parapeito ()
  (cn7_verylayer jnl_layc_ppl 7)
  (setvar "cecolor" jnl_layc_ppc)
  (setvar "celtype" "bylayer")
  (command "._line" "_non" jnl_cxi1 "_non" jnl_cxi2 "")
  (command "._line" "_non" jnl_cxi3 "_non" jnl_cxi4 "")
)

(defun jnl_draw_parapeito_1 ()
  (cn7_verylayer jnl_layc_ppl 7)
  (setvar "cecolor" jnl_layc_ppc)
  (setvar "celtype" "bylayer")
  (command "._line" "_non" jnl_cxi1 "_non" jnl_cxi2 "")
)

;*****************************************
;Desenho de Caixilho                      
;*****************************************

(defun jnl_draw_caixilho ()
  (if (/= 0.0 jnl_caix)
    ;se o caixilho não for nulo
    (progn
      (setq jnl_cxi1 (polar jnl_brk1 jnl_angbase jnl_caix)
	    jnl_cxi2 (polar jnl_cxi1 jnl_angbase jnl_larg)
	    jnl_cxi3 (polar jnl_brk3 jnl_angbase jnl_caix)
	    jnl_cxi4 (polar jnl_cxi3 jnl_angbase jnl_larg)
      )
      (if (= jnl_visible 1)
	(progn
	  (cn7_verylayer jnl_layc_cxl 7)
	  (setvar "cecolor" jnl_layc_cxc)
	  (command "._line"  "_non" jnl_brk1 "_non" jnl_cxi1  "_non" jnl_cxi3 "_non" jnl_brk3 "" 
		   "._line"  "_non" jnl_brk2 "_non" jnl_cxi2  "_non" jnl_cxi4 "_non" jnl_brk4 "" 
          )
	)
	(progn
	  (cn7_verylayer jnl_layc_prl 7)
	  (setvar "cecolor" jnl_layc_prc)
	  (if (not (tblsearch "ltype" "hidden2"))
	    (command "._linetype" "_l" "hidden2" (strcat cnp_root "/modelos/cadnorma.lin") "")
	    (command "._linetype" "_l" "hidden2" (strcat cnp_root "/modelos/cadnorma.lin") "_y" "")
          )
	  (setvar "celtype" "hidden2")
	  (command "._line" "_non" jnl_brk1 "_non" jnl_brk3 "" "._chprop" (entlast) "" "_s" 0.5 ""
		   "._line" "_non" jnl_cxi1 "_non" jnl_cxi3 "" "._chprop" (entlast) "" "_s" 0.5 ""
		   "._line" "_non" jnl_brk2 "_non" jnl_brk4 "" "._chprop" (entlast) "" "_s" 0.5 ""
		   "._line" "_non" jnl_cxi2 "_non" jnl_cxi4 "" "._chprop" (entlast) "" "_s" 0.5 ""
          )
	)
      )
    )
    ;se o caixilho for nulo
    (progn
      (setq jnl_cxi1 jnl_brk1
	    jnl_cxi2 jnl_brk2
	    jnl_cxi3 jnl_brk3
	    jnl_cxi4 jnl_brk4
      )
      (if (= jnl_visible 0)
	(progn
	  (cn7_verylayer jnl_layc_prl 7)
	  (setvar "cecolor" jnl_layc_prc)
	  (if (not (tblsearch "ltype" "hidden2"))
	    (command "._linetype" "_l" "hidden2" (strcat cnp_root "/modelos/cadnorma.lin") "")
	    (command "._linetype" "_l" "hidden2" (strcat cnp_root "/modelos/cadnorma.lin") "_y" "")
          )
	  (setvar "celtype" "hidden2")
	  (command "._line" "_non" jnl_brk1 "_non" jnl_brk3 "" "._chprop" (entlast) "" "_s" 0.5 ""
		   "._line" "_non" jnl_brk2 "_non" jnl_brk4 "" "._chprop" (entlast) "" "_s" 0.5 ""
          )
	)
      )
    )
  )
)


;*****************************************
;Funções auxiliares comuns                
;*****************************************

;testa a visibilidade
(defun jnl_test_visible ()
  (if (= jnl_visible 1)
    (progn
      (cn7_verylayer jnl_layc_vil 7)
      (setvar "cecolor" jnl_layc_vic)
    )
    (progn
      (cn7_verylayer jnl_layc_prl 7)
      (setvar "cecolor" jnl_layc_prc)
      (if (not (tblsearch "ltype" "hidden2"))
	(command "._linetype" "_l" "hidden2" (strcat cnp_root "/modelos/cadnorma.lin") "")
	(command "._linetype" "_l" "hidden2" (strcat cnp_root "/modelos/cadnorma.lin") "_y" "")
      )
      (setvar "celtype" "hidden2")
    )
  )
)

;estabelece os pontos principais para construção das janelas
(defun jnl_openfree_mark ()
  (command "._undo" "_m")
  ;conversão de dados para numerais
  (if (= jnl_var_lrad "jnl_larg_radio1")
    (setq jnl_larg (* jnl_fator (distof jnl_var_larg)))
    (setq jnl_larg (* jnl_fator (distof jnl_var_diam)))
  )
  (jnl_halt_file)
  (setq jnl_halt (* jnl_fator (distof (nth (fix (distof jnl_var_halt)) jnl_halt_list)))
	jnl_afas (* jnl_fator (distof jnl_var_afas))
	jnl_wall (* jnl_fator (distof jnl_var_wall))
	jnl_caix (* jnl_fator (distof jnl_var_caix))
  )
  ;clica na parede
  (prompt "\nSelecione a parede interna...")
  (setq jnl_entsel (entsel)
	jnl_ent1 (car jnl_entsel)
	jnl_ent1_type (cdr (assoc 0 (entget jnl_ent1)))
	jnl_pt0 (nth 0 (cdr jnl_entsel))
	jnl_ptt1 (cdr (assoc 10 (entget jnl_ent1)))
	jnl_ptt2 (cdr (assoc 11 (entget jnl_ent1)))
	jnl_wall_layer (cdr (assoc 8 (entget jnl_ent1)))
  )
  (if (/= "LINE" jnl_ent1_type)
    (progn
      (alert "A entidade Selecionada não é uma 'LINE'.\nPOLYLINES devem ser explodidas\npara usar este comando...")
      (jnl_openfree_mark)
    )
  )
  (if (<= (distance jnl_pt0 jnl_ptt1) (distance jnl_pt0 jnl_ptt2))
    (setq jnl_pt1 jnl_ptt1 jnl_pt2 jnl_ptt2 jnl_code 1)
    (setq jnl_pt1 jnl_ptt2 jnl_pt2 jnl_ptt1 jnl_code 2)
  )
  (setq jnl_angbase (angle jnl_pt1 jnl_pt2))
  ;verifica o posicionamento para determinar os pontos de quebra
  (if (= jnl_var_posi "jnl_center")
    (setq jnl_doll (/ (- (distance jnl_pt1 jnl_pt2) jnl_larg (* 2 jnl_caix)) 2))
    (setq jnl_doll jnl_afas)
  )
  (setq
	jnl_brk1 (polar jnl_pt1 jnl_angbase jnl_doll)
	jnl_brk2 (polar jnl_brk1 jnl_angbase (+ jnl_larg (* 2 jnl_caix)))
  )
  (if (= jnl_code 1)
    (setq jnl_brk3a (polar jnl_brk1 (- jnl_angbase (/ pi 2)) jnl_wall)
	  jnl_brk3b (polar jnl_brk1 (+ jnl_angbase (/ pi 2)) jnl_wall)
	  jnl_brk4a (polar jnl_brk2 (- jnl_angbase (/ pi 2)) jnl_wall)
	  jnl_brk4b (polar jnl_brk2 (+ jnl_angbase (/ pi 2)) jnl_wall)
    )
    (setq jnl_brk3a (polar jnl_brk1 (+ jnl_angbase (/ pi 2)) jnl_wall)
  	  jnl_brk3b (polar jnl_brk1 (- jnl_angbase (/ pi 2)) jnl_wall)
	  jnl_brk4a (polar jnl_brk2 (+ jnl_angbase (/ pi 2)) jnl_wall)
	  jnl_brk4b (polar jnl_brk2 (- jnl_angbase (/ pi 2)) jnl_wall)
    )
  )
  (if (/= nil (ssget "_f" (list jnl_brk3a jnl_brk4a) (list (cons 8 jnl_wall_layer))))
    (progn
      (setq jnl_brk3 jnl_brk3a jnl_brk4 jnl_brk4a jnl_xcode 1)
      (setq jnl_brkm (polar jnl_brk3 (angle jnl_brk3 jnl_brk4) (/ (distance jnl_brk3 jnl_brk4) 2)))
      (if (= nil (ssget "c" jnl_brkm jnl_brkm))
	(progn
	  (setq jnl_brk3 jnl_brk3b jnl_brk4 jnl_brk4b)
	  (setq jnl_brkm (polar jnl_brk3 (angle jnl_brk3 jnl_brk4) (/ (distance jnl_brk3 jnl_brk4) 2))
		jnl_xcode 2)
	)
      )
    )
    (progn
      (setq jnl_brk3 jnl_brk3b jnl_brk4 jnl_brk4b jnl_xcode 2)
      (setq jnl_brkm (polar jnl_brk3 (angle jnl_brk3 jnl_brk4) (/ (distance jnl_brk3 jnl_brk4) 2)))
      (if (= nil (ssget "c" jnl_brkm jnl_brkm))
	(progn
	  (setq jnl_brk3 jnl_brk3a jnl_brk4 jnl_brk4a)
	  (setq jnl_brkm (polar jnl_brk3 (angle jnl_brk3 jnl_brk4) (/ (distance jnl_brk3 jnl_brk4) 2))
		jnl_xcode 4)
	)
      )
    )
  )
  (setq jnl_angortho (angle jnl_brk1 jnl_brk3))
  (setq jnl_mid1 (polar jnl_brk1 jnl_angbase (/ (distance jnl_brk1 jnl_brk2) 2.0))
	jnl_mid2 (polar jnl_brk3 jnl_angbase (/ (distance jnl_brk3 jnl_brk4) 2.0))
  )

)

;faz a quebra para janelas visíveis (em vista)
(defun jnl_openfree_break ()
  (setvar "cecolor" "bylayer")
  (setvar "celtype" "bylayer")
  (command "._break" jnl_ent1 "_non" jnl_brk1 "_non" jnl_brk2)
  (command "._break" (ssget "c" jnl_brkm jnl_brkm) "_non" jnl_brk3 "_non" jnl_brk4)
  (command "._layer" "_s" jnl_wall_layer "")
  (command "._line" "_non" jnl_brk1 "_non" jnl_brk3 "" "._line" "_non" jnl_brk2 "_non" jnl_brk4 "")
)


;procedimento padrão par todas as janelas
(defun jnl_start ()
  (cn7_init)
  (guarda '("blipmode" "cecolor" "celtype" "clayer" "cmdecho" "orthomode"
          "textstyle" "luprec" "osmode" ))
  (setvar "cecolor" "bylayer")
  (jnl_last_file)
  (jnl_layc_file)
  (jnl_iden_file)
  (cond
    ((= cn7_dwgunit 1) (setq jnl_fator 0.01 jnl_blkscl 1.0))
    ((= cn7_dwgunit 100) (setq jnl_fator 1.0 jnl_blkscl 100.0))
    ((= cn7_dwgunit 1000) (setq jnl_fator 10.0 jnl_blkscl 1000.0))
  )
  (jnl_openfree_mark)
)


;***********************************
;Configuração de Identificação      
;***********************************

;caixa de diálogo
(defun jnl_cfgiden_button ()
  (jnl_iden_file)
  (setq dcl_id (load_dialog (strcat cnp_root "/lisp/cadnorma.dcl")))
  (if (not (new_dialog "jnl_cfgiden" dcl_id)) (exit))
  ;preenche os slides
  (jnl_iden_upslides)
  (setq x (dimx_tile "jnl_cfgiden_typ")
	y (dimy_tile "jnl_cfgiden_typ"))
  (start_image "jnl_cfgiden_typ")
  (fill_image  0 0 x y -2)
  (slide_image 0 0 x y (strcat cnp_root "/slides/jnl_iden" jnl_iden_typ ".sld"))
  (end_image)
  ;estilos de texto
  (setq jnl_iden_stylist (list "r50" "r60" "r70" "r80" "r90" "r100" "r120" "r140" "r175" "r200"
			       "t1" "t2" "t3" "t4" "t5" "t6" "t7"))
  (start_list "jnl_cfgiden_sty")
  (mapcar 'add_list jnl_iden_stylist)
  (end_list)
  (set_tile "jnl_cfgiden_sty" jnl_iden_sty)
  (action_tile "jnl_cfgiden_sty" "(setq jnl_iden_sty $value)")
  ;cor dos elementos
  (start_image "jnl_cfgiden_col")
  (fill_image  0  0
    (dimx_tile "jnl_cfgiden_col")
    (dimy_tile "jnl_cfgiden_col")
    (fix (distof jnl_iden_col))
  )
  (end_image)
  (action_tile "jnl_cfgiden_col" "(jnl_idencol_action)")
  ;layer da identificação
  (set_tile "jnl_cfgiden_lay" jnl_iden_lay)
  (action_tile "jnl_cfgiden_lay" "(setq jnl_iden_lay $value)")
  ;botões principais
  (action_tile "cancel" "(done_dialog 0)")
  (action_tile "accept" "(done_dialog 1)")
  (setq jnl_idendcl_id (start_dialog))
  (unload_dialog dcl_id)
  (if (= 1 jnl_idendcl_id) (jnl_iden_writefile))
  (jnl_main)
)


;escolher a cor do identificador
(defun jnl_idencol_action ()
  (setq jnl_iden_newcol (acad_colordlg (fix (distof jnl_iden_col))))
  (if (/= nil jnl_iden_newcol) (setq jnl_iden_col (rtos jnl_iden_newcol 2 0)))
  (start_image "jnl_cfgiden_col")
  (fill_image  0  0
    (dimx_tile "jnl_cfgiden_col")
    (dimy_tile "jnl_cfgiden_col")
    (fix (distof jnl_iden_col))
  )
  (end_image)
)


;atualiza os slides a atribui actions
(defun jnl_iden_upslides ()
  (setq x (dimx_tile "iden11")
	y (dimy_tile "iden11"))
  (start_image "iden11")
  (slide_image 0 0 x y (strcat cnp_root "/slides/jnl_iden11.sld"))
  (end_image)
  (action_tile "iden11" "(jnl_cfgiden_seltype)")
  (setq x (dimx_tile "iden12")
	y (dimy_tile "iden12"))
  (start_image "iden12")
  (slide_image 0 0 x y (strcat cnp_root "/slides/jnl_iden12.sld"))
  (end_image)
  (action_tile "iden12" "(jnl_cfgiden_seltype)")
  (setq x (dimx_tile "iden13")
	y (dimy_tile "iden13"))
  (start_image "iden13")
  (slide_image 0 0 x y (strcat cnp_root "/slides/jnl_iden13.sld"))
  (end_image)
  (action_tile "iden13" "(jnl_cfgiden_seltype)")
  (setq x (dimx_tile "iden21")
	y (dimy_tile "iden21"))
  (start_image "iden21")
  (slide_image 0 0 x y (strcat cnp_root "/slides/jnl_iden21.sld"))
  (end_image)
  (action_tile "iden21" "(jnl_cfgiden_seltype)")
  (setq x (dimx_tile "iden22")
	y (dimy_tile "iden22"))
  (start_image "iden22")
  (slide_image 0 0 x y (strcat cnp_root "/slides/jnl_iden22.sld"))
  (end_image)
  (action_tile "iden22" "(jnl_cfgiden_seltype)")
  (setq x (dimx_tile "iden23")
	y (dimy_tile "iden23"))
  (start_image "iden23")
  (slide_image 0 0 x y (strcat cnp_root "/slides/jnl_iden23.sld"))
  (end_image)
  (action_tile "iden23" "(jnl_cfgiden_seltype)")
)

;ao selecionar um slide
(defun jnl_cfgiden_seltype ()
  (setq jnl_iden_tipo $key
	jnl_iden_typ (substr jnl_iden_tipo 5 2)
  )
  (setq x (dimx_tile "jnl_cfgiden_typ")
	y (dimy_tile "jnl_cfgiden_typ"))
  (start_image "jnl_cfgiden_typ")
  (fill_image  0 0 x y -2)
  (slide_image 0 0 x y (strcat cnp_root "/slides/jnl_iden" jnl_iden_typ ".sld"))
  (end_image)
)


;lê os dados iniciais da DCL no arquivo de dados
(defun jnl_iden_file ()
  (if (findfile (strcat cnp_root "/config/jnl_iden.txt"))
    (jnl_iden_readfile)
    (progn
      (setq file (open (strcat cnp_root "/config/jnl_iden.txt") "w" "utf8"))
      (write-line "11" file)
      (write-line "5" file)
      (write-line "2" file)
      (write-line "Janela_ident" file)
      (close file)
      (jnl_iden_readfile)
    )
  )
)

;função que lê o arquivo de dados
(defun jnl_iden_readfile ()
  (setq	file (open (strcat cnp_root "/config/jnl_iden.txt") "r" "utf8"))
  (setq	jnl_iden_typ (read-line file))
  (setq	jnl_iden_sty (read-line file))
  (setq	jnl_iden_col (read-line file))
  (setq	jnl_iden_lay (read-line file))
  (close file)
)

;função que escreve o arquivo de dados
(defun jnl_iden_writefile ()
  (setq	file (open (strcat cnp_root "/config/jnl_iden.txt") "w" "utf8"))
  (write-line jnl_iden_typ file)
  (write-line jnl_iden_sty file)
  (write-line jnl_iden_col file)
  (write-line jnl_iden_lay file)
  (close file)
)

;***********************************
;identificação das janelas          
;***********************************
(defun c:idj () (jnl_identify))

(defun jnl_identify ()
  (jnl_iden_file)
  (setq dzinmo (getvar "dimzin"))
  (setvar "dimzin" 4)
  (setq jnl_iden_stylist (list "r50" "r60" "r70" "r80" "r90" "r100" "r120" "r140" "r175" "r200"
			       "t1" "t2" "t3" "t4" "t5" "t6" "t7")
	jnl_doiden_sty (nth (fix (distof jnl_iden_sty)) jnl_iden_stylist)
  )
  ;texto de largura
  (setq jnl_iden_prefix "" jnl_iden_larg jnl_larg)
  (cond
    ((= cn7_dwgunit 1.0);desenho em metros
     (if (> jnl_iden_larg 1.0)
       (setq jnl_doiden_larg (rtos jnl_iden_larg 2 2))
       (setq jnl_doiden_larg (rtos (* jnl_iden_larg 100.0) 2 0))
     )
    )
    ((= cn7_dwgunit 100.0);desenho em centímetros
     (setq jnl_doiden_larg (rtos (* jnl_iden_larg 1.0) 2 0))
    )
    ((= cn7_dwgunit 1000.0);desenho em milímetros
     (setq jnl_doiden_larg (rtos (/ jnl_iden_larg 10.0) 2 0))
    )
  )
  ;texto da altura
  (setq jnl_doiden_halt (nth (fix (distof jnl_var_halt)) jnl_halt_list)
	jnl_doiden_halt (/ (distof jnl_doiden_halt) 100.0)
  )
  (if (> jnl_doiden_halt 1.0)
    (setq jnl_doiden_halt (rtos jnl_doiden_halt 2 2))
    (setq jnl_doiden_halt (rtos (* jnl_doiden_halt 100.0) 2 0))
  )
  (setvar "dimzin" dzinmo)
  ;define o texto pelo tipo de identificação
  (cond
    ((or (= jnl_iden_typ "11") (= jnl_iden_typ "21") (= jnl_iden_typ "22"))
     (if (= jnl_var_lrad "jnl_larg_radio1")
       (setq jnl_iden_text1 (strcat jnl_iden_prefix jnl_doiden_larg "x" jnl_doiden_halt))
       (setq jnl_iden_text1 (strcat "%%c"jnl_iden_prefix jnl_doiden_larg))
     )
    )
    ((= jnl_iden_typ "13")
     (if (= jnl_var_lrad "jnl_larg_radio1")
       (setq jnl_iden_text1 (strcat "J(" jnl_iden_prefix jnl_doiden_larg ")"))
       (setq jnl_iden_text1 (strcat "J(%%c" jnl_iden_prefix jnl_doiden_larg ")"))
     )
    )
  )
  (if (or (= jnl_iden_typ "21") (= jnl_iden_typ "22") (= jnl_iden_typ "23"))
     (jnl_iden_getcode)
  )
  (jnl_iden_write)
)

;escreve o texto identificador
(defun jnl_iden_write ()
  (setq pt1 nil psimb_txt nil jnl_iden_ang nil)
  (setq psimb_txt (getpoint "\nPonto de inserção do identificador..."))
  (initget 128)
  (setq pt1 (getpoint psimb_txt "\nAlinhado/Ortogonal/<Ângulo do identificador (ENTER=0)>: "))
  (cond
    ;se clicar num ponto
    ((= 'LIST (type pt1))
     (setq jnl_iden_ang (angle psimb_txt pt1))
    )
    ((= 'STR  (type pt1))
     (cond       
       ((= "A" (strcase pt1))
	(setq jnl_iden_ang jnl_angbase)
       )
       ((= "O" (strcase pt1))
	(setq jnl_iden_ang (+ jnl_angortho pi))
       )
       (t
	(prompt "\nOpção inválida... Marque o ponto, digite <A> ou <R> para determinar o ângulo...")
	(jnl_iden_write)
       )
     )
   )
  )
  (if (= jnl_iden_ang nil) (setq jnl_iden_ang 0.0))
  (if (> jnl_iden_ang (* 2 pi)) (setq jnl_iden_ang (- jnl_iden_ang (* 2 pi))))
  (setq jnl_saveang jnl_iden_ang
	jnl_iden_ang (/ (* 180 jnl_iden_ang) pi)
  )
  (if (and (> jnl_iden_ang 90) (<= jnl_iden_ang 270))
    (setq jnl_iden_ang (+ jnl_iden_ang 180))
  )
  (setvar "celtype" "bylayer")
  (setvar "cecolor" "bylayer")
  (cond
    ((= jnl_iden_typ "11")
     (cn7_txsimb jnl_doiden_sty "_c" jnl_iden_text1 (fix (distof jnl_iden_col)) jnl_iden_lay jnl_iden_ang)
    )
    ((= jnl_iden_typ "12")
     (if (= jnl_var_lrad "jnl_larg_radio1")
       (progn
	 (cn7_txsimb jnl_doiden_sty "_c" jnl_doiden_larg (fix (distof jnl_iden_col)) jnl_iden_lay jnl_iden_ang)
	 (setq pt1 psimb_txt)
	 (setq psimb_txt (polar psimb_txt (/ (* pi (- jnl_iden_ang 90)) 180) (* cn7_txth 2)))
	 (cn7_txsimb jnl_doiden_sty "_c" jnl_doiden_halt (fix (distof jnl_iden_col)) jnl_iden_lay jnl_iden_ang)
	 (setq pt2 (polar pt1 (angle pt1 psimb_txt) (/ (distance pt1 psimb_txt) 4))
	       pt3 (polar pt2 jnl_saveang (* cn7_txth 2.5))
	       pt4 (polar pt2 (+ jnl_saveang pi) (* cn7_txth 2.5))
	 )
	 (cn7_verylayer (strcat cn7_prefixlay jnl_iden_lay) (fix (distof jnl_iden_col)))
	 (command "._line" "_non" pt3 "_non" pt4 "")
       )
       (progn
	 (cn7_txsimb jnl_doiden_sty "_c" (strcat "%%c" jnl_doiden_larg)
	   (fix (distof jnl_iden_col)) jnl_iden_lay jnl_iden_ang)
	 (setq pt1 psimb_txt)
	 (setq psimb_txt (polar psimb_txt (/ (* pi (- jnl_iden_ang 90)) 180) (* cn7_txth 2)))
;;;	 (cn7_txsimb jnl_doiden_sty "_c" jnl_doiden_halt (fix (distof jnl_iden_col)) jnl_iden_lay jnl_iden_ang)
	 (setq pt2 (polar pt1 (angle pt1 psimb_txt) (/ (distance pt1 psimb_txt) 4))
	       pt3 (polar pt2 jnl_saveang (* cn7_txth 2.5))
	       pt4 (polar pt2 (+ jnl_saveang pi) (* cn7_txth 2.5))
	 )
	 (cn7_verylayer (strcat cn7_prefixlay jnl_iden_lay) (fix (distof jnl_iden_col)))
	 (command "._line" "_non" pt3 "_non" pt4 "")
       )
     )
    )
    ((= jnl_iden_typ "13")
     (cn7_txsimb jnl_doiden_sty "_c" jnl_iden_text1 (fix (distof jnl_iden_col)) jnl_iden_lay jnl_iden_ang)
    )
    ((= jnl_iden_typ "21")
     (cn7_txsimb jnl_doiden_sty "_c" jnl_iden_code1 (fix (distof jnl_iden_col)) jnl_iden_lay jnl_iden_ang)
     (setq pt1 psimb_txt)
     (setq psimb_txt (polar psimb_txt (/ (* pi (- jnl_iden_ang 90)) 180) (* cn7_txth 2)))
     (cn7_txsimb jnl_doiden_sty "_c" jnl_iden_text1 (fix (distof jnl_iden_col)) jnl_iden_lay jnl_iden_ang)
     (setq pt2 (polar pt1 (angle pt1 psimb_txt) (/ (distance pt1 psimb_txt) 4))
	   pt3 (polar pt2 jnl_saveang (* cn7_txth 4.0))
	   pt4 (polar pt2 (+ jnl_saveang pi) (* cn7_txth 4.0))
     )
     (cn7_verylayer (strcat cn7_prefixlay jnl_iden_lay) (fix (distof jnl_iden_col)))
     (command "._line" "_non" pt3 "_non" pt4 "")
    )
    ((= jnl_iden_typ "22")
     (cn7_txsimb jnl_doiden_sty "_c" (strcat jnl_iden_code1 "(" jnl_iden_text1 ")")
       (fix (distof jnl_iden_col)) jnl_iden_lay jnl_iden_ang)
    )
    ((= jnl_iden_typ "23")
     (cn7_txsimb jnl_doiden_sty "_c" jnl_iden_code1 (fix (distof jnl_iden_col)) jnl_iden_lay jnl_iden_ang)
    )
   );cond
)

	
;coleta o código da porta
(defun jnl_iden_getcode ()
  (if (= nil jnl_iden_code1) (setq jnl_iden_code1 "J1"))
  (setq dcl_id (load_dialog (strcat cnp_root "/lisp/cadnorma.dcl")))
  (if (not (new_dialog "jnl_iden_gcode" dcl_id)) (exit))
  (set_tile "jnl_gcode_code" jnl_iden_code1)
  (mode_tile "jnl_gcode_code" 2)
  (action_tile "jnl_gcode_code" "(setq jnl_iden_code1 $value)")
  (action_tile "cancel" "(done_dialog 0)")
  (action_tile "accept" "(done_dialog 1)")
  (setq jnl_gcode_dclid (start_dialog))
  (unload_dialog dcl_id)
)


;cnp_21_e_portas

;Cadnorma Professional
;Super Programa de Portas
;iniciado em 10/12/10

;programa de portas
(defun c:pt ()
  ;arquivo inicial
  (prt_last_file)
  (prt_main)
)

;aber a DCL principal
(defun prt_main ()
  (cn7_init)
  ;abre a caixa de diálogo
  (setq dcl_id (load_dialog (strcat cnp_root "/lisp/cadnorma.dcl")))
  (if (not (new_dialog "porta" dcl_id)) (exit))
  (prt_update_slides)
  ;lista de larguras
  (prt_larg_file)
  (prt_larg_buildlista)
  (set_tile "prt_dcl_larg" prt_var_larg)
  (action_tile "prt_dcl_larg" "(setq prt_var_larg $value)")
  (action_tile "prt_larg_edit" "(done_dialog 2)")
  ;lista de alturas
  (prt_halt_file)
  (start_list "prt_dcl_halt")
  (mapcar 'add_list prt_halt_list)
  (end_list)
  (set_tile "prt_dcl_halt" prt_var_halt)
  (action_tile "prt_dcl_halt" "(setq prt_var_halt $value)")
  (action_tile "prt_halt_edit" "(done_dialog 3)")
  ;vão livre
  (set_tile "prt_getlvao_edit" prt_var_lvao)
  (action_tile "prt_getlvao_edit" "(prt_getlvao_editaction)")
  ;Definições por opção de largura
  (prt_larg_def)
  (action_tile "prt_larg_radio1" "(prt_larg_radio_action)")
  (action_tile "prt_larg_radio2" "(prt_larg_radio_action)")
  (action_tile "prt_getlarg_pick" "(done_dialog 10)")
  ;slide do Tipo Atual
  (setq x (dimx_tile "prt_slide_type")
	y (dimy_tile "prt_slide_type")
  )
  (start_image "prt_slide_type")
  (fill_image 0 0 x y -2)
  (slide_image 0 0 x y (strcat cnp_root "/slides/prt_" prt_var_tipo ".sld"))
  (end_image)
  ;Posicionamento
  (set_tile "prt_posi" prt_var_posi)
  (if (= "prt_center" prt_var_posi)
    (mode_tile "prt_afas_edit" 1)
    (mode_tile "prt_afas_edit" 0)
  )
  (action_tile "prt_posi" "(prt_posi_action)")
  ;afastamento
  (set_tile "prt_afas_edit" prt_var_afas)
  (action_tile "prt_afas_edit" "(prt_getafas_editaction)")
  (action_tile "prt_get_afas" "(done_dialog 9)")
  ;parede
  (set_tile "prt_wall_edit" prt_var_wall)
  (action_tile "prt_wall_edit" "(prt_getwall_editaction)")
  (action_tile "prt_get_wall" "(done_dialog 4)")
  ;caixilho
  (set_tile "prt_caix_edit" prt_var_caix)
  (action_tile "prt_caix_edit" "(prt_getcaix_editaction)")
  (action_tile "prt_get_caix" "(done_dialog 5)")
  ;código de identificação
  (set_tile "prt_iden_toggle" prt_var_iden)
  (action_tile "prt_iden_toggle" "(setq prt_var_iden $value)")
  (action_tile "prt_iden_button" "(done_dialog 6)")
  ;configurar layers e cores
  (action_tile "prt_cfg_laycol" "(done_dialog 7)")
  ;tipo de identificador
  (action_tile "prt_cfg_detype" "(done_dialog 8)")
  (action_tile "cancel" "(done_dialog 0)")
  (action_tile "accept" "(done_dialog 1)")
  ;ativação da DCL
  (setq prt_dcl_id (start_dialog))
  (unload_dialog dcl_id)
  ;ações dos botões
  (if (= 1 prt_dcl_id) (prt_ok_action))
  (if (= 2 prt_dcl_id) (prt_largedit_action))
  (if (= 3 prt_dcl_id) (prt_haltedit_action))
  (if (= 4 prt_dcl_id) (prt_getwall_button))
  (if (= 5 prt_dcl_id) (prt_getcaix_button))
  (if (= 6 prt_dcl_id) (prt_cfgiden_button))
  (if (= 7 prt_dcl_id) (prt_laycol_button))
  (if (= 8 prt_dcl_id) (prt_detype_button))
  (if (= 9 prt_dcl_id) (prt_getafas_button))
  (if (= 10 prt_dcl_id) (prt_getlvao_button))
  (princ)
)


;ao selecionar o rádio 1 ou 2
(defun prt_larg_radio_action ()
  (setq prt_var_lrad $key)
  (prt_larg_def)
  (if (= prt_var_lrad "prt_larg_radio2")
    (mode_tile "prt_getlvao_edit" 2)
  )
)

;método de determinação da largura
(defun prt_larg_def ()
  (if (= prt_var_lrad "prt_larg_radio1")
    (progn
      (set_tile "prt_larg_radio1" "1")
      (set_tile "prt_larg_radio2" "0")
      (mode_tile "prt_getlvao_edit" 1)
      (mode_tile "prt_getlarg_pick" 1)
      (mode_tile "prt_dcl_larg" 0)
      (mode_tile "prt_larg_edit" 0)
    )
    (progn
      (set_tile "prt_larg_radio1" "0")
      (set_tile "prt_larg_radio2" "1")
      (mode_tile "prt_getlvao_edit" 0)
      (mode_tile "prt_getlarg_pick" 0)
      (mode_tile "prt_dcl_larg" 1)
      (mode_tile "prt_larg_edit" 1)
    )
  )
)

;ao clicar no botão "ok"
(defun prt_ok_action ()
;;;  (prt_last_writefile)
  (cond
    ((= prt_var_tipo "11") (prt_drw11))
    ((= prt_var_tipo "12") (prt_drw12))
    ((= prt_var_tipo "13") (prt_drw13))
    ((= prt_var_tipo "14") (prt_drw14))
    ((= prt_var_tipo "21") (prt_drw21))
    ((= prt_var_tipo "22") (prt_drw22))
    ((= prt_var_tipo "23") (prt_drw23))
    ((= prt_var_tipo "24") (prt_drw24))
    ((= prt_var_tipo "31") (prt_drw31))
    ((= prt_var_tipo "32") (prt_drw32))
    ((= prt_var_tipo "33") (prt_drw33))
    ((= prt_var_tipo "34") (prt_drw34))
    ((= prt_var_tipo "41") (prt_drw41))
    ((= prt_var_tipo "42") (prt_drw42))
    ((= prt_var_tipo "43") (prt_drw43))
    ((= prt_var_tipo "44") (prt_drw44))
  )
  (if (= prt_var_iden "1")
    (prt_identify)
  )
)

;***********************************
;Detalhes de Tipos                  
;***********************************

;gerenciador
(defun prt_detype_button ()
;;;  (prt_last_writefile)
  (cond
    ((= prt_var_tipo "11") (prt_cfg_11) (prt_main))
    ((= prt_var_tipo "12") (prt_cfg_12) (prt_main))
    ((= prt_var_tipo "13") (prt_cfg_13) (prt_main))
    ((= prt_var_tipo "14") (prt_cfg_14) (prt_main))
    ((= prt_var_tipo "21") (prt_cfg_21) (prt_main))
    ((= prt_var_tipo "22") (prt_cfg_22) (prt_main))
    ((= prt_var_tipo "23") (prt_cfg_23) (prt_main))
    ((= prt_var_tipo "24") (prt_cfg_24) (prt_main))
    ((= prt_var_tipo "31") (prt_cfg_31) (prt_main))
    ((= prt_var_tipo "32") (prt_cfg_32) (prt_main))
    ((= prt_var_tipo "33") (prt_cfg_33) (prt_main))
    ((= prt_var_tipo "34") (prt_cfg_34) (prt_main))
    ((= prt_var_tipo "41") (prt_cfg_41) (prt_main))
    ((= prt_var_tipo "42") (prt_cfg_42) (prt_main))
    ((= prt_var_tipo "43") (prt_cfg_43) (prt_main))
    ((= prt_var_tipo "44") (prt_cfg_44) (prt_main))
  )
)


;***********************************
;Configuração de Cores e Layers     
;***********************************
(defun prt_laycol_button ()
  (prt_layc_file)
  (setq dcl_id (load_dialog (strcat cnp_root "/lisp/cadnorma.dcl")))
  (if (not (new_dialog "prt_cfglayc" dcl_id)) (exit))
  ;porta
  (set_tile "prt_layc_pol" prt_layc_pol)
  (action_tile "prt_layc_pol" "(setq prt_layc_pol $value)")
  (start_image "prt_layc_poc")
  (fill_image  0  0
    (dimx_tile "prt_layc_poc")
    (dimy_tile "prt_layc_poc")
    (fix (distof prt_layc_poc))
  )
  (end_image)
  (action_tile "prt_layc_poc" "(prt_layc_poc_color)")
  ;caixilho
  (set_tile "prt_layc_cxl" prt_layc_cxl)
  (action_tile "prt_layc_cxl" "(setq prt_layc_cxl $value)")
  (start_image "prt_layc_cxc")
  (fill_image  0  0
    (dimx_tile "prt_layc_cxc")
    (dimy_tile "prt_layc_cxc")
    (fix (distof prt_layc_cxc))
  )
  (end_image)
  (action_tile "prt_layc_cxc" "(prt_layc_cxc_color)")
  ;Maçaneta
  (set_tile "prt_layc_mal" prt_layc_mal)
  (action_tile "prt_layc_mal" "(setq prt_layc_mal $value)")
  (start_image "prt_layc_mac")
  (fill_image  0  0
    (dimx_tile "prt_layc_mac")
    (dimy_tile "prt_layc_mac")
    (fix (distof prt_layc_mac))
  )
  (end_image)
  (action_tile "prt_layc_mac" "(prt_layc_mac_color)")
  ;Soleira
  (set_tile "prt_layc_sol" prt_layc_sol)
  (action_tile "prt_layc_sol" "(setq prt_layc_sol $value)")
  (start_image "prt_layc_soc")
  (fill_image  0  0
    (dimx_tile "prt_layc_soc")
    (dimy_tile "prt_layc_soc")
    (fix (distof prt_layc_soc))
  )
  (end_image)
  (action_tile "prt_layc_soc" "(prt_layc_soc_color)")
  ;Alisares
  (set_tile "prt_layc_all" prt_layc_all)
  (action_tile "prt_layc_all" "(setq prt_layc_all $value)")
  (start_image "prt_layc_alc")
  (fill_image  0  0
    (dimx_tile "prt_layc_alc")
    (dimy_tile "prt_layc_alc")
    (fix (distof prt_layc_alc))
  )
  (end_image)
  (action_tile "prt_layc_alc" "(prt_layc_alc_color)")
  ;Arcos
  (set_tile "prt_layc_arl" prt_layc_arl)
  (action_tile "prt_layc_arl" "(setq prt_layc_arl $value)")
  (start_image "prt_layc_arc")
  (fill_image  0  0
    (dimx_tile "prt_layc_arc")
    (dimy_tile "prt_layc_arc")
    (fix (distof prt_layc_arc))
  )
  (end_image)
  (action_tile "prt_layc_arc" "(prt_layc_arc_color)")
  ;ok_cancel
  (action_tile "cancel" "(done_dialog 0)")
  (action_tile "accept" "(done_dialog 1)")
  ;start_dialog
  (setq prt_layc_id (start_dialog))
  (unload_dialog dcl_id)
  (if (= prt_layc_id 1)
    (progn
      (prt_layc_writefile)
      (prt_main)
    )
  )
  (if (= prt_layc_id 0) (prt_main))
)

;escolher cor dos Arcos
(defun prt_layc_arc_color ()
  (setq prt_layc_arc_newcol (acad_colordlg (fix (distof prt_layc_arc))))
  (if (/= nil prt_layc_arc_newcol) (setq prt_layc_arc (rtos prt_layc_arc_newcol 2 0)))
  (start_image "prt_layc_arc")
  (fill_image  0  0
    (dimx_tile "prt_layc_arc")
    (dimy_tile "prt_layc_arc")
    (fix (distof prt_layc_arc))
  )
  (end_image)
)


;escolher cor dos Alisares
(defun prt_layc_alc_color ()
  (setq prt_layc_alc_newcol (acad_colordlg (fix (distof prt_layc_alc))))
  (if (/= nil prt_layc_alc_newcol) (setq prt_layc_alc (rtos prt_layc_alc_newcol 2 0)))
  (start_image "prt_layc_alc")
  (fill_image  0  0
    (dimx_tile "prt_layc_alc")
    (dimy_tile "prt_layc_alc")
    (fix (distof prt_layc_alc))
  )
  (end_image)
)

;escolher cor da Soleira
(defun prt_layc_soc_color ()
  (setq prt_layc_soc_newcol (acad_colordlg (fix (distof prt_layc_soc))))
  (if (/= nil prt_layc_soc_newcol) (setq prt_layc_soc (rtos prt_layc_soc_newcol 2 0)))
  (start_image "prt_layc_soc")
  (fill_image  0  0
    (dimx_tile "prt_layc_soc")
    (dimy_tile "prt_layc_soc")
    (fix (distof prt_layc_soc))
  )
  (end_image)
)


;escolher cor da Maçaneta
(defun prt_layc_mac_color ()
  (setq prt_layc_mac_newcol (acad_colordlg (fix (distof prt_layc_mac))))
  (if (/= nil prt_layc_mac_newcol) (setq prt_layc_mac (rtos prt_layc_mac_newcol 2 0)))
  (start_image "prt_layc_mac")
  (fill_image  0  0
    (dimx_tile "prt_layc_mac")
    (dimy_tile "prt_layc_mac")
    (fix (distof prt_layc_mac))
  )
  (end_image)
)

;escolher cor do caixilho
(defun prt_layc_cxc_color ()
  (setq prt_layc_cxc_newcol (acad_colordlg (fix (distof prt_layc_cxc))))
  (if (/= nil prt_layc_cxc_newcol) (setq prt_layc_cxc (rtos prt_layc_cxc_newcol 2 0)))
  (start_image "prt_layc_cxc")
  (fill_image  0  0
    (dimx_tile "prt_layc_cxc")
    (dimy_tile "prt_layc_cxc")
    (fix (distof prt_layc_cxc))
  )
  (end_image)
)

;escolher cor da porta
(defun prt_layc_poc_color ()
  (setq prt_layc_poc_newcol (acad_colordlg (fix (distof prt_layc_poc))))
  (if (/= nil prt_layc_poc_newcol) (setq prt_layc_poc (rtos prt_layc_poc_newcol 2 0)))
  (start_image "prt_layc_poc")
  (fill_image  0  0
    (dimx_tile "prt_layc_poc")
    (dimy_tile "prt_layc_poc")
    (fix (distof prt_layc_poc))
  )
  (end_image)
)


;lê os dados iniciais da DCL no arquivo de dados
(defun prt_layc_file ()
  (if (findfile (strcat cnp_root "/config/prt_layc.txt"))
    (prt_layc_readfile)
    (progn
      (setq file (open (strcat cnp_root "/config/prt_layc.txt") "w" "utf8"))
      (write-line "Porta" file)
      (write-line "2" file)      
      (write-line "Porta_caixilho" file)
      (write-line "2" file)
      (write-line "Porta_Soleira" file)
      (write-line "1" file)
      (write-line "Porta_Maçaneta" file)
      (write-line "1" file)
      (write-line "Porta_Alisar" file)
      (write-line "1" file)
      (write-line "Porta" file)
      (write-line "1" file)
      (close file)
      (prt_layc_readfile)
    )
  )
)

;função que lê o arquivo de dados
(defun prt_layc_readfile ()
  (setq	file (open (strcat cnp_root "/config/prt_layc.txt") "r" "utf8"))
  (setq	prt_layc_pol (read-line file))
  (setq	prt_layc_poc (read-line file))
  (setq	prt_layc_cxl (read-line file))
  (setq	prt_layc_cxc (read-line file))
  (setq	prt_layc_sol (read-line file))
  (setq	prt_layc_soc (read-line file))
  (setq	prt_layc_mal (read-line file))
  (setq	prt_layc_mac (read-line file))
  (setq	prt_layc_all (read-line file))
  (setq	prt_layc_alc (read-line file))
  (setq	prt_layc_arl (read-line file))
  (setq	prt_layc_arc (read-line file))
  (close file)
)

;função que escreve o arquivo de dados
(defun prt_layc_writefile ()
  (setq	file (open (strcat cnp_root "/config/prt_layc.txt") "w" "utf8"))
  (write-line prt_layc_pol file)
  (write-line prt_layc_poc file)
  (write-line prt_layc_cxl file)
  (write-line prt_layc_cxc file)
  (write-line prt_layc_sol file)
  (write-line prt_layc_soc file)
  (write-line prt_layc_mal file)
  (write-line prt_layc_mac file)
  (write-line prt_layc_all file)
  (write-line prt_layc_alc file)
  (write-line prt_layc_arl file)
  (write-line prt_layc_arc file)
  (close file)
)


;***********************************
;Configuração de Identificação      
;***********************************

;caixa de diálogo
(defun prt_cfgiden_button ()
  (prt_iden_file)
  (setq dcl_id (load_dialog (strcat cnp_root "/lisp/cadnorma.dcl")))
  (if (not (new_dialog "prt_cfgiden" dcl_id)) (exit))
  ;preenche os slides
  (prt_iden_upslides)
  (setq x (dimx_tile "prt_cfgiden_typ")
	y (dimy_tile "prt_cfgiden_typ"))
  (start_image "prt_cfgiden_typ")
  (fill_image  0 0 x y -2)
  (slide_image 0 0 x y (strcat cnp_root "/slides/prt_iden" prt_iden_typ ".sld"))
  (end_image)
  ;estilos de texto
  (setq prt_iden_stylist (list "r50" "r60" "r70" "r80" "r90" "r100" "r120" "r140" "r175" "r200"
			       "t1" "t2" "t3" "t4" "t5" "t6" "t7"))
  (start_list "prt_cfgiden_sty")
  (mapcar 'add_list prt_iden_stylist)
  (end_list)
  (set_tile "prt_cfgiden_sty" prt_iden_sty)
  (action_tile "prt_cfgiden_sty" "(setq prt_iden_sty $value)")
  ;cor dos elementos
  (start_image "prt_cfgiden_col")
  (fill_image  0  0
    (dimx_tile "prt_cfgiden_col")
    (dimy_tile "prt_cfgiden_col")
    (fix (distof prt_iden_col))
  )
  (end_image)
  (action_tile "prt_cfgiden_col" "(prt_idencol_action)")
  ;layer da identificação
  (set_tile "prt_cfgiden_lay" prt_iden_lay)
  (action_tile "prt_cfgiden_lay" "(setq prt_iden_lay $value)")
  ;botões principais
  (action_tile "cancel" "(done_dialog 0)")
  (action_tile "accept" "(done_dialog 1)")
  (setq prt_idendcl_id (start_dialog))
  (unload_dialog dcl_id)
  (if (= 1 prt_idendcl_id) (prt_iden_writefile))
  (prt_main)
)


;escolher a cor do identificador
(defun prt_idencol_action ()
  (setq prt_iden_newcol (acad_colordlg (fix (distof prt_iden_col))))
  (if (/= nil prt_iden_newcol) (setq prt_iden_col (rtos prt_iden_newcol 2 0)))
  (start_image "prt_cfgiden_col")
  (fill_image  0  0
    (dimx_tile "prt_cfgiden_col")
    (dimy_tile "prt_cfgiden_col")
    (fix (distof prt_iden_col))
  )
  (end_image)
)


;atualiza os slides a atribui actions
(defun prt_iden_upslides ()
  (setq x (dimx_tile "iden11")
	y (dimy_tile "iden11"))
  (start_image "iden11")
  (slide_image 0 0 x y (strcat cnp_root "/slides/prt_iden11.sld"))
  (end_image)
  (action_tile "iden11" "(prt_cfgiden_seltype)")
  (setq x (dimx_tile "iden12")
	y (dimy_tile "iden12"))
  (start_image "iden12")
  (slide_image 0 0 x y (strcat cnp_root "/slides/prt_iden12.sld"))
  (end_image)
  (action_tile "iden12" "(prt_cfgiden_seltype)")
  (setq x (dimx_tile "iden13")
	y (dimy_tile "iden13"))
  (start_image "iden13")
  (slide_image 0 0 x y (strcat cnp_root "/slides/prt_iden13.sld"))
  (end_image)
  (action_tile "iden13" "(prt_cfgiden_seltype)")
  (setq x (dimx_tile "iden21")
	y (dimy_tile "iden21"))
  (start_image "iden21")
  (slide_image 0 0 x y (strcat cnp_root "/slides/prt_iden21.sld"))
  (end_image)
  (action_tile "iden21" "(prt_cfgiden_seltype)")
  (setq x (dimx_tile "iden22")
	y (dimy_tile "iden22"))
  (start_image "iden22")
  (slide_image 0 0 x y (strcat cnp_root "/slides/prt_iden22.sld"))
  (end_image)
  (action_tile "iden22" "(prt_cfgiden_seltype)")
  (setq x (dimx_tile "iden23")
	y (dimy_tile "iden23"))
  (start_image "iden23")
  (slide_image 0 0 x y (strcat cnp_root "/slides/prt_iden23.sld"))
  (end_image)
  (action_tile "iden23" "(prt_cfgiden_seltype)")
)

;ao selecionar um slide
(defun prt_cfgiden_seltype ()
  (setq prt_iden_tipo $key
	prt_iden_typ (substr prt_iden_tipo 5 2)
  )
  (setq x (dimx_tile "prt_cfgiden_typ")
	y (dimy_tile "prt_cfgiden_typ"))
  (start_image "prt_cfgiden_typ")
  (fill_image  0 0 x y -2)
  (slide_image 0 0 x y (strcat cnp_root "/slides/prt_iden" prt_iden_typ ".sld"))
  (end_image)
)


;lê os dados iniciais da DCL no arquivo de dados
(defun prt_iden_file ()
  (if (findfile (strcat cnp_root "/config/prt_iden.txt"))
    (prt_iden_readfile)
    (progn
      (setq file (open (strcat cnp_root "/config/prt_iden.txt") "w" "utf8"))
      (write-line "11" file)
      (write-line "5" file)
      (write-line "2" file)
      (write-line "Porta_ident" file)
      (close file)
      (prt_iden_readfile)
    )
  )
)

;função que lê o arquivo de dados
(defun prt_iden_readfile ()
  (setq	file (open (strcat cnp_root "/config/prt_iden.txt") "r" "utf8"))
  (setq	prt_iden_typ (read-line file))
  (setq	prt_iden_sty (read-line file))
  (setq	prt_iden_col (read-line file))
  (setq	prt_iden_lay (read-line file))
  (close file)
)

;função que escreve o arquivo de dados
(defun prt_iden_writefile ()
  (setq	file (open (strcat cnp_root "/config/prt_iden.txt") "w" "utf8"))
  (write-line prt_iden_typ file)
  (write-line prt_iden_sty file)
  (write-line prt_iden_col file)
  (write-line prt_iden_lay file)
  (close file)
)

;***********************************
;identificação das portas
;***********************************
(defun c:idp () (prt_identify))

(defun prt_identify ()
  (prt_iden_file)
  (setq dzinmo (getvar "dimzin"))
  (setvar "dimzin" 4)
  (setq prt_iden_stylist (list "r50" "r60" "r70" "r80" "r90" "r100" "r120" "r140" "r175" "r200"
			       "t1" "t2" "t3" "t4" "t5" "t6" "t7")
	prt_doiden_sty (nth (fix (distof prt_iden_sty)) prt_iden_stylist)
  )
  ;texto de largura
  (cond
    ((or (= prt_var_tipo "11") (= prt_var_tipo "13") (= prt_var_tipo "14")
	 (= prt_var_tipo "21") (= prt_var_tipo "23") (= prt_var_tipo "41") (= prt_var_tipo "43"))
     (setq prt_iden_prefix "" prt_iden_larg prt_larg))
    ((or (= prt_var_tipo "12") (= prt_var_tipo "31") (= prt_var_tipo "42") (= prt_var_tipo "44"))
     (setq prt_iden_prefix "2x" prt_iden_larg (/ prt_larg 2.0)))
    ((= prt_var_tipo "22") (setq prt_iden_prefix "2x" prt_iden_larg prt_larg))
    ((= prt_var_tipo "24") (setq prt_iden_prefix (strcat prt_pt24_qtd "x")
				 prt_iden_larg (/ prt_larg (distof prt_pt24_qtd))))
    ((= prt_var_tipo "32")
     (setq prt_iden_prefix "3x" prt_iden_larg (/ prt_larg 3.0)))
    ((= prt_var_tipo "33")
     (setq prt_iden_prefix "4x" prt_iden_larg (/ prt_larg 4.0)))
    ((= prt_var_tipo "34") (setq prt_iden_prefix (strcat prt_pt34_qtd "x")
				 prt_iden_larg (/ prt_larg (distof prt_pt34_qtd))))
  )
  (cond
    ((= cn7_dwgunit 1.0);desenho em metros
     (if (> prt_iden_larg 1.0)
       (setq prt_doiden_larg (rtos prt_iden_larg 2 2))
       (setq prt_doiden_larg (rtos (* prt_iden_larg 100.0) 2 0))
     )
    )
    ((= cn7_dwgunit 100.0);desenho em centímetros
     (setq prt_doiden_larg (rtos (* prt_iden_larg 1.0) 2 0))
    )
    ((= cn7_dwgunit 1000.0);desenho em milímetros
     (setq prt_doiden_larg (rtos (/ prt_iden_larg 10.0) 2 0))
    )
  )
  ;texto da altura
  (setq prt_doiden_halt (nth (fix (distof prt_var_halt)) prt_halt_list)
	prt_doiden_halt (/ (distof prt_doiden_halt) 100.0)
  )
  (if (> prt_doiden_halt 1.0)
    (setq prt_doiden_halt (rtos prt_doiden_halt 2 2))
    (setq prt_doiden_halt (rtos (* prt_doiden_halt 100.0) 2 0))
  )
  (setvar "dimzin" dzinmo)
  ;define o texto pelo tipo de identificação
  (cond
    ((or (= prt_iden_typ "11") (= prt_iden_typ "21") (= prt_iden_typ "22"))
     (setq prt_iden_text1 (strcat prt_iden_prefix prt_doiden_larg "x" prt_doiden_halt))
    )
    ((= prt_iden_typ "13")
     (setq prt_iden_text1 (strcat "P(" prt_iden_prefix prt_doiden_larg ")"))
    )
  )
  (if (or (= prt_iden_typ "21") (= prt_iden_typ "22") (= prt_iden_typ "23"))
     (prt_iden_getcode)
  )
  (prt_iden_write)
)

;escreve o texto identificador
(defun prt_iden_write ()
  (setq pt1 nil psimb_txt nil prt_iden_ang nil)
  (setq psimb_txt (getpoint "\nPonto de inserção do identificador..."))
  (initget 128)
  (setq pt1 (getpoint psimb_txt "\nAlinhado/Ortogonal/<Ângulo do identificador (ENTER=0)>: "))
  (cond
    ;se clicar num ponto
    ((= 'LIST (type pt1))
     (setq prt_iden_ang (angle psimb_txt pt1))
    )
    ((= 'STR  (type pt1))
     (cond       
       ((= "A" (strcase pt1))
	(setq prt_iden_ang prt_angbase)
       )
       ((= "O" (strcase pt1))
	(setq prt_iden_ang (+ prt_angortho pi))
       )
       (t
	(prompt "\nOpção inválida... Marque o ponto, digite <A> ou <R> para determinar o ângulo...")
	(prt_iden_write)
       )
     )
   )
  )
  (if (= prt_iden_ang nil) (setq prt_iden_ang 0.0))
  (if (> prt_iden_ang (* 2 pi)) (setq prt_iden_ang (- prt_iden_ang (* 2 pi))))
  (setq prt_saveang prt_iden_ang
	prt_iden_ang (/ (* 180 prt_iden_ang) pi)
  )
  (if (and (> prt_iden_ang 90) (<= prt_iden_ang 270))
    (setq prt_iden_ang (+ prt_iden_ang 180))
  )
  (cond
    ((= prt_iden_typ "11")
     (cn7_txsimb prt_doiden_sty "_c" prt_iden_text1 (fix (distof prt_iden_col)) prt_iden_lay prt_iden_ang)
    )
    ((= prt_iden_typ "12")
     (cn7_txsimb prt_doiden_sty "_c" prt_doiden_larg (fix (distof prt_iden_col)) prt_iden_lay prt_iden_ang)
     (setq pt1 psimb_txt)
     (setq psimb_txt (polar psimb_txt (/ (* pi (- prt_iden_ang 90)) 180) (* cn7_txth 2)))
     (cn7_txsimb prt_doiden_sty "_c" prt_doiden_halt (fix (distof prt_iden_col)) prt_iden_lay prt_iden_ang)
     (setq pt2 (polar pt1 (angle pt1 psimb_txt) (/ (distance pt1 psimb_txt) 4))
	   pt3 (polar pt2 prt_saveang (* cn7_txth 2.5))
	   pt4 (polar pt2 (+ prt_saveang pi) (* cn7_txth 2.5))
     )
     (cn7_verylayer (strcat cn7_prefixlay prt_iden_lay) (fix (distof prt_iden_col)))
     (command "._line" "_non" pt3 "_non" pt4 "")
    )
    ((= prt_iden_typ "13")
     (cn7_txsimb prt_doiden_sty "_c" prt_iden_text1 (fix (distof prt_iden_col)) prt_iden_lay prt_iden_ang)
    )
    ((= prt_iden_typ "21")
     (cn7_txsimb prt_doiden_sty "_c" prt_iden_code1 (fix (distof prt_iden_col)) prt_iden_lay prt_iden_ang)
     (setq pt1 psimb_txt)
     (setq psimb_txt (polar psimb_txt (/ (* pi (- prt_iden_ang 90)) 180) (* cn7_txth 2)))
     (cn7_txsimb prt_doiden_sty "_c" prt_iden_text1 (fix (distof prt_iden_col)) prt_iden_lay prt_iden_ang)
     (setq pt2 (polar pt1 (angle pt1 psimb_txt) (/ (distance pt1 psimb_txt) 4))
	   pt3 (polar pt2 prt_saveang (* cn7_txth 4.0))
	   pt4 (polar pt2 (+ prt_saveang pi) (* cn7_txth 4.0))
     )
     (cn7_verylayer (strcat cn7_prefixlay prt_iden_lay) (fix (distof prt_iden_col)))
     (command "._line" "_non" pt3 "_non" pt4 "")
    )
    ((= prt_iden_typ "22")
     (cn7_txsimb prt_doiden_sty "_c" (strcat prt_iden_code1 "(" prt_iden_text1 ")")
       (fix (distof prt_iden_col)) prt_iden_lay prt_iden_ang)
    )
    ((= prt_iden_typ "23")
     (cn7_txsimb prt_doiden_sty "_c" prt_iden_code1 (fix (distof prt_iden_col)) prt_iden_lay prt_iden_ang)
    )
   );cond
)

	
;coleta o código da porta
(defun prt_iden_getcode ()
  (if (= nil prt_iden_code1) (setq prt_iden_code1 "P1"))
  (setq dcl_id (load_dialog (strcat cnp_root "/lisp/cadnorma.dcl")))
  (if (not (new_dialog "prt_iden_gcode" dcl_id)) (exit))
  (set_tile "prt_gcode_code" prt_iden_code1)
  (mode_tile "prt_gcode_code" 2)
  (action_tile "prt_gcode_code" "(setq prt_iden_code1 $value)")
  (action_tile "cancel" "(done_dialog 0)")
  (action_tile "accept" "(done_dialog 1)")
  (setq prt_gcode_dclid (start_dialog))
  (unload_dialog dcl_id)
)


;***********************************
;Configuração de Caixilho           
;***********************************
(defun prt_getcaix_button ()
;;;  (prt_last_writefile)
  (setq caix_dist nil
	pt1 (getpoint "\nPrimeiro ponto da parede...: ")
	pt2 (getpoint pt1 "Segundo ponto da parede... ")
	caix_dist (distance pt1 pt2)
  )
  (cond
    ((= cn7_dwgunit 1.0) (setq new_dist (* caix_dist 100.0)))
    ((= cn7_dwgunit 100.0) (setq new_dist (* caix_dist 1.0)))
    ((= cn7_dwgunit 1000.0) (setq new_dist (* caix_dist 0.1)))
  )
  (if new_dist
    (progn
      (setq prt_var_caix (rtos new_dist 2 2))
;;;      (prt_last_writefile)
    )
  )
  (prt_main)
)

;verifica se o valor entrado é válido
(defun prt_getcaix_editaction ()
  (setq prt_var_newcaix $value)
  (if (distof prt_var_newcaix)
    (setq prt_var_caix prt_var_newcaix)
    (progn
      (alert "Valor Inválido!")
      (set_tile "prt_caix_edit" prt_var_caix)
      (mode_tile "prt_caix_edit" 2)
    )
  )
)  


;***********************************
;Espessura de Paredes               
;***********************************

;clica em dois pontos = nova espessura de paredes
(defun prt_getwall_button ()
;;;  (prt_last_writefile)
  (setq wall_dist nil
	pt1 (getpoint "\nPrimeiro ponto da parede...: ")
	pt2 (getpoint pt1 "Segundo ponto da parede... ")
	wall_dist (distance pt1 pt2)
  )
  (cond
    ((= cn7_dwgunit 1.0) (setq new_dist (* wall_dist 100.0)))
    ((= cn7_dwgunit 100.0) (setq new_dist (* wall_dist 1.0)))
    ((= cn7_dwgunit 1000.0) (setq new_dist (* wall_dist 0.1)))
  )
  (if new_dist
    (progn
      (setq prt_var_wall (rtos new_dist 2 2))
;;;      (prt_last_writefile)
    )
  )
  (prt_main)
)
  
  

;verifica se o valor entrado é válido
(defun prt_getwall_editaction ()
  (setq prt_var_newwall $value)
  (if (distof prt_var_newwall)
    (setq prt_var_wall prt_var_newwall)
    (progn
      (alert "Valor Inválido!")
      (set_tile "prt_wall_edit" prt_var_wall)
      (mode_tile "prt_wall_edit" 2)
    )
  )
)  

;***********************************
;Posicionamento e Afastamento       
;***********************************

;ao selecionar a posição da porta
(defun prt_posi_action ()
  (setq prt_var_posi $value)
  (if (= "prt_center" prt_var_posi)
    (mode_tile "prt_afas_edit" 1)
    (progn
      (mode_tile "prt_afas_edit" 0)
      (mode_tile "prt_afas_edit" 2)
    )
  )
)

;verifica se o valor entrado é válido para vão livre
(defun prt_getlvao_editaction ()
  (setq prt_var_newlvao $value)
  (if (distof prt_var_newlvao)
    (setq prt_var_lvao prt_var_newlvao)
    (progn
      (alert "Valor Inválido!\nDigite um número Real.")
      (set_tile "prt_getlvao_edit" prt_var_lvao)
      (mode_tile "prt_getlvao_edit" 2)
    )
  )
)  
  
;verifica se o valor entrado é válido
(defun prt_getafas_editaction ()
  (setq prt_var_newafas $value)
  (if (distof prt_var_newafas)
    (setq prt_var_afas prt_var_newafas)
    (progn
      (alert "Valor Inválido!")
      (set_tile "prt_afas_edit" prt_var_afas)
      (mode_tile "prt_afas_edit" 2)
    )
  )
)  

;clica em dois pontos = novo vão livre
(defun prt_getlvao_button ()
;;;  (prt_last_writefile)
  (setq lvao_dist nil
	pt1 (getpoint "\nPrimeiro ponto para definir o vão livre...: ")
	pt2 (getpoint pt1 "Segundo ponto para definir o vão livre...: ")
	lvao_dist (distance pt1 pt2)
  )
  (cond
    ((= cn7_dwgunit 1.0) (setq new_dist (* lvao_dist 100.0)))
    ((= cn7_dwgunit 100.0) (setq new_dist (* lvao_dist 1.0)))
    ((= cn7_dwgunit 1000.0) (setq new_dist (* lvao_dist 0.1)))
  )
  (if new_dist
    (progn
      (setq prt_var_lvao (rtos new_dist 2 2))
;;;      (prt_last_writefile)
    )
  )
  (prt_main)
)


;clica em dois pontos = novo afastamento
(defun prt_getafas_button ()
;;;  (prt_last_writefile)
  (setq afas_dist nil
	pt1 (getpoint "\nPrimeiro ponto do afastamento...: ")
	pt2 (getpoint pt1 "Segundo ponto do afastamento... ")
	afas_dist (distance pt1 pt2)
  )
  (cond
    ((= cn7_dwgunit 1.0) (setq new_dist (* afas_dist 100.0)))
    ((= cn7_dwgunit 100.0) (setq new_dist (* afas_dist 1.0)))
    ((= cn7_dwgunit 1000.0) (setq new_dist (* afas_dist 0.1)))
  )
  (if new_dist
    (progn
      (setq prt_var_afas (rtos new_dist 2 2))
;;;      (prt_last_writefile)
    )
  )
  (prt_main)
)

  
;********************
;Alturas             
;********************

;edição de alturas
(defun prt_haltedit_action ()
  (setq prt_cfghalt_sel prt_var_halt)
  (setq dcl_id (load_dialog (strcat cnp_root "/lisp/cadnorma.dcl")))
  (if (not (new_dialog "prt_edit_halt" dcl_id)) (exit))
  (prt_halt_file);-> prt_halt_list
  (start_list "prt_cfghalt_list")
  (mapcar 'add_list prt_halt_list)
  (end_list)
  (set_tile "prt_cfghalt_list" prt_cfghalt_sel)
;;;  (cond
;;;    ((= "0" prt_cfghalt_sel)
;;;     (mode_tile "prt_cfghalt_up" 1)
;;;     (mode_tile "prt_cfghalt_down" 0)
;;;    )
;;;    ((= prt_cfghalt_sel (rtos (1- halt_list_len) 2 0))
;;;     (mode_tile "prt_cfghalt_up" 0)
;;;     (mode_tile "prt_cfghalt_down" 1)
;;;    )
;;;    (t
;;;     (mode_tile "prt_cfghalt_up" 0)
;;;     (mode_tile "prt_cfghalt_down" 0)
;;;    )     
;;;  )
  (action_tile "prt_cfghalt_list" "(prt_cfghalt_selist)")
  (action_tile "prt_cfghalt_up" "(prt_cfghalt_up)")
  (action_tile "prt_cfghalt_down" "(prt_cfghalt_down)")
  (action_tile "cancel" "(done_dialog 0)")
  (action_tile "accept" "(done_dialog 1)")
  (action_tile "prt_cfghalt_add" "(done_dialog 2)")
  (action_tile "prt_cfghalt_del" "(prt_cfghalt_delete)")
  (setq prt_halt_dclid (start_dialog))
  (unload_dialog dcl_id)
  (if (= 0 prt_halt_dclid) (prt_main))
  (if (= 1 prt_halt_dclid) (prt_cfghalt_ok))
  (if (= 2 prt_halt_dclid) (prt_cfghalt_addaction))
)


;Arquivos de configuração de alturas
(defun prt_halt_file ()
  (if (findfile (strcat cnp_root "/config/prt_altura.txt"))
    (prt_halt_readfile)
    (progn
      (setq file (open (strcat cnp_root "/config/prt_altura.txt") "w" "utf8"))
      (write-line "210" file)
      (write-line "220" file)
      (write-line "240" file)
      (close file)
      (prt_halt_readfile)
    )
  )
)

;lâ a lista de alturas disponíveis
(defun prt_halt_readfile ()
  (setq file (open (strcat cnp_root "/config/prt_altura.txt") "r" "utf8"))
  (setq prt_halt_list (list))
  (while (/= nil (setq linha (read-line file)))
    (setq prt_halt_list (append prt_halt_list (list linha)))
  )
  (close file)
)

;escreve a lista de alturas disponíveis
(defun prt_halt_writefile ()
  (setq file (open (strcat cnp_root "/config/prt_altura.txt") "w" "utf8"))
  (foreach n prt_halt_list
    (write-line n file)
  )
  (close file)
)


;botão ok
(defun prt_cfghalt_ok ()
  (prt_halt_writefile)
  (prt_main)
)

;botão Excluir
(defun prt_cfghalt_delete ()
  (setq counter 0
	halt_list_len (length prt_halt_list)
	new_list (list)
  )
  (repeat halt_list_len
    (if (/= counter (fix (distof prt_cfghalt_sel)))
      (setq new_list (append new_list (list (nth counter prt_halt_list))))
    )
    (setq counter (1+ counter))
  )
  (setq prt_halt_list new_list)
  (start_list "prt_cfghalt_list")
  (mapcar 'add_list prt_halt_list)
  (end_list)
  (set_tile "prt_cfghalt_list" prt_cfghalt_sel)
)
	    

;botão Adicionar
(defun prt_cfghalt_addaction ()
  (setq prt_gethalt_nova nil)
  (setq dcl_id (load_dialog (strcat cnp_root "/lisp/cadnorma.dcl")))
  (if (not (new_dialog "prt_halt_getnew" dcl_id)) (exit))
  (mode_tile "prt_halt_getnew_edit" 2)
  (action_tile "prt_halt_getnew_edit" "(setq prt_gethalt_nova $value)")
  (action_tile "cancel" "(done_dialog 0)")
  (action_tile "accept" "(done_dialog 1)")
  (setq prt_gethalt_dclid (start_dialog))
  (unload_dialog dcl_id)
  (if (= 1 prt_gethalt_dclid)
    (if (and (/= nil prt_gethalt_nova)
	     (/= "" prt_gethalt_nova)
	     (distof prt_gethalt_nova)
	)
      (progn
	(setq prt_halt_list (append prt_halt_list (list prt_gethalt_nova)))
	(prt_halt_writefile)
	(prt_halt_file)
        (prt_haltedit_action)
      )
    )
  )
)

;ao selecionar um item da lista
(defun prt_cfghalt_selist ()
  (setq prt_cfghalt_sel $value
	halt_list_len (length prt_halt_list)
  )
  (cond
    ((= "0" prt_cfghalt_sel)
     (mode_tile "prt_cfghalt_up" 1)
     (mode_tile "prt_cfghalt_down" 0)
    )
    ((= prt_cfghalt_sel (rtos (1- halt_list_len) 2 0))
     (mode_tile "prt_cfghalt_up" 0)
     (mode_tile "prt_cfghalt_down" 1)
    )
    (t
     (mode_tile "prt_cfghalt_up" 0)
     (mode_tile "prt_cfghalt_down" 0)
    )     
  )
)

;ação para o botão "up"
(defun prt_cfghalt_up ()
  (setq halt_1 (fix (distof prt_cfghalt_sel));selecionado
	halt_2 (1- halt_1);subir
	counter 0
	new_list2 (list))
  (while (< counter (length prt_halt_list))
    (if (= counter halt_2)
      (progn
	(setq new_list2 (append new_list2 (list (nth (1+ counter) prt_halt_list))))
	(setq new_list2 (append new_list2 (list (nth counter prt_halt_list))))
	(setq counter (+ 2 counter))
      )
      (progn
	(setq new_list2 (append new_list2 (list (nth counter prt_halt_list))))
	(setq counter (1+ counter))
      )
    )
  )
  (setq prt_halt_list new_list2)
  (start_list "prt_cfghalt_list")
  (mapcar 'add_list prt_halt_list)
  (end_list)
  (setq prt_cfghalt_sel (rtos (1- (fix (distof prt_cfghalt_sel))) 2 0))
  (set_tile "prt_cfghalt_list" prt_cfghalt_sel)
  (cond
    ((= "0" prt_cfghalt_sel)
     (mode_tile "prt_cfghalt_up" 1)
     (mode_tile "prt_cfghalt_down" 0)
    )
    ((= prt_cfghalt_sel (rtos (1- halt_list_len) 2 0))
     (mode_tile "prt_cfghalt_up" 0)
     (mode_tile "prt_cfghalt_down" 1)
    )
    (t
     (mode_tile "prt_cfghalt_up" 0)
     (mode_tile "prt_cfghalt_down" 0)
    )     
  )
)

;ação para o botão "down"
(defun prt_cfghalt_down ()
  (setq halt_1 (fix (distof prt_cfghalt_sel));selecionado
	halt_2 (1+ halt_1);subir
	counter 0
	new_list2 (list))
  (while (< counter (length prt_halt_list))
    (if (= counter halt_1)
      (progn
	(setq new_list2 (append new_list2 (list (nth (1+ counter) prt_halt_list))))
	(setq new_list2 (append new_list2 (list (nth counter prt_halt_list))))
	(setq counter (+ 2 counter))
      )
      (progn
	(setq new_list2 (append new_list2 (list (nth counter prt_halt_list))))
	(setq counter (1+ counter))
      )
    )
  )
  (setq prt_halt_list new_list2)
  (start_list "prt_cfghalt_list")
  (mapcar 'add_list prt_halt_list)
  (end_list)
  (setq prt_cfghalt_sel (rtos (1+ (fix (distof prt_cfghalt_sel))) 2 0))
  (set_tile "prt_cfghalt_list" prt_cfghalt_sel)
  (cond
    ((= "0" prt_cfghalt_sel)
     (mode_tile "prt_cfghalt_up" 1)
     (mode_tile "prt_cfghalt_down" 0)
    )
    ((= prt_cfghalt_sel (rtos (1- halt_list_len) 2 0))
     (mode_tile "prt_cfghalt_up" 0)
     (mode_tile "prt_cfghalt_down" 1)
    )
    (t
     (mode_tile "prt_cfghalt_up" 0)
     (mode_tile "prt_cfghalt_down" 0)
    )     
  )
)

;*****************
;Lista de Larguras
;*****************

;atualiza as larguras disponíveis
(defun prt_larg_buildlista ()
  (cond
    ((or (= prt_var_tipo "11") (= prt_var_tipo "13") (= prt_var_tipo "14")
	 (= prt_var_tipo "21") (= prt_var_tipo "23") (= prt_var_tipo "24")
	 (= prt_var_tipo "34") (= prt_var_tipo "43")
     )
     (setq prt_larg_lista prt_larg_list)
    )
    ((or (= prt_var_tipo "12") (= prt_var_tipo "22") (= prt_var_tipo "31")
	 (= prt_var_tipo "41") (= prt_var_tipo "44")
     )
     (setq prt_larg_lista (list))
     (foreach n prt_larg_list
       (setq prt_larg_lista (append prt_larg_lista (list (strcat "2 x " n))))
     )
    )
    ((or (= prt_var_tipo "32"))
     (setq prt_larg_lista (list))
     (foreach n prt_larg_list
       (setq prt_larg_lista (append prt_larg_lista (list (strcat "3 x " n))))
     )
    )
    ((or (= prt_var_tipo "33") (= prt_var_tipo "42"))
     (setq prt_larg_lista (list))
     (foreach n prt_larg_list
       (setq prt_larg_lista (append prt_larg_lista (list (strcat "4 x " n))))
     )
    )
  );cond
  (start_list "prt_dcl_larg")
  (mapcar 'add_list prt_larg_lista)
  (end_list)
  (set_tile "prt_dcl_larg" prt_var_larg)
)

;lê a lista de larguras disponíveis
(defun prt_larg_file ()
  (if (findfile (strcat cnp_root "/config/prt_largura.txt"))
    (prt_larg_readfile)
    (progn
      (setq file (open (strcat cnp_root "/config/prt_largura.txt") "w" "utf8"))
      (write-line "40" file)
      (write-line "50" file)
      (write-line "60" file)
      (write-line "70" file)
      (write-line "80" file)
      (write-line "90" file)
      (write-line "100" file)
      (write-line "110" file)
      (write-line "120" file)
      (write-line "140" file)
      (write-line "160" file)
      (write-line "180" file)
      (write-line "200" file)
      (close file)
      (prt_larg_readfile)
    )
  )
)

;lâ a lista de larguras disponíveis
(defun prt_larg_readfile ()
  (setq file (open (strcat cnp_root "/config/prt_largura.txt") "r" "utf8"))
  (setq prt_larg_list (list))
  (while (/= nil (setq linha (read-line file)))
    (setq prt_larg_list (append prt_larg_list (list linha)))
  )
  (close file)
)

;escreve a lista de larguras editada
(defun prt_larg_writefile ()
  (setq file (open (strcat cnp_root "/config/prt_largura.txt") "w" "utf8"))
  (foreach n prt_larg_list
    (write-line n file)
  )
  (close file)
)

;edição de larguras
(defun prt_largedit_action ()
  (setq prt_cfglarg_sel prt_var_larg)
  (setq dcl_id (load_dialog (strcat cnp_root "/lisp/cadnorma.dcl")))
  (if (not (new_dialog "prt_edit_larg" dcl_id)) (exit))
  (prt_larg_file);-> prt_larg_list
  (start_list "prt_cfglarg_list")
  (mapcar 'add_list prt_larg_list)
  (end_list)
  (set_tile "prt_cfglarg_list" prt_cfglarg_sel)
  (action_tile "prt_cfglarg_list" "(prt_cfglarg_selist)")
  (action_tile "prt_cfglarg_up" "(prt_cfglarg_up)")
  (action_tile "prt_cfglarg_down" "(prt_cfglarg_down)")
  (action_tile "cancel" "(done_dialog 0)")
  (action_tile "accept" "(done_dialog 1)")
  (action_tile "prt_cfglarg_add" "(done_dialog 2)")
  (action_tile "prt_cfglarg_del" "(prt_cfglarg_delete)")
  (setq prt_larg_dclid (start_dialog))
  (unload_dialog dcl_id)
  (if (= 0 prt_larg_dclid) (prt_main))
  (if (= 1 prt_larg_dclid) (prt_cfglarg_ok))
  (if (= 2 prt_larg_dclid) (prt_cfglarg_addaction))
)

;botão ok
(defun prt_cfglarg_ok ()
  (prt_larg_writefile)
  (prt_main)
)

;botão Excluir
(defun prt_cfglarg_delete ()
  (setq counter 0
	larg_list_len (length prt_larg_list)
	new_list (list)
  )
  (repeat larg_list_len
    (if (/= counter (fix (distof prt_cfglarg_sel)))
      (setq new_list (append new_list (list (nth counter prt_larg_list))))
    )
    (setq counter (1+ counter))
  )
  (setq prt_larg_list new_list)
  (start_list "prt_cfglarg_list")
  (mapcar 'add_list prt_larg_list)
  (end_list)
  (set_tile "prt_cfglarg_list" prt_cfglarg_sel)
)
	    

;botão Adicionar
(defun prt_cfglarg_addaction ()
  (setq prt_getlarg_nova nil)
  (setq dcl_id (load_dialog (strcat cnp_root "/lisp/cadnorma.dcl")))
  (if (not (new_dialog "prt_larg_getnew" dcl_id)) (exit))
  (mode_tile "prt_larg_getnew_edit" 2)
  (action_tile "prt_larg_getnew_edit" "(setq prt_getlarg_nova $value)")
  (action_tile "cancel" "(done_dialog 0)")
  (action_tile "accept" "(done_dialog 1)")
  (setq prt_getlarg_dclid (start_dialog))
  (unload_dialog dcl_id)
  (if (= 1 prt_getlarg_dclid)
    (if (and (/= nil prt_getlarg_nova)
	     (/= "" prt_getlarg_nova)
	     (distof prt_getlarg_nova)
	)
      (progn
	(setq prt_larg_list (append prt_larg_list (list prt_getlarg_nova)))
	(prt_larg_writefile)
	(prt_larg_file)
        (prt_largedit_action)
      )
    )
  )
)

;ao selecionar um item da lista
(defun prt_cfglarg_selist ()
  (setq prt_cfglarg_sel $value
	larg_list_len (length prt_larg_list)
  )
  (cond
    ((= "0" prt_cfglarg_sel)
     (mode_tile "prt_cfglarg_up" 1)
     (mode_tile "prt_cfglarg_down" 0)
    )
    ((= prt_cfglarg_sel (rtos (1- larg_list_len) 2 0))
     (mode_tile "prt_cfglarg_up" 0)
     (mode_tile "prt_cfglarg_down" 1)
    )
    (t
     (mode_tile "prt_cfglarg_up" 0)
     (mode_tile "prt_cfglarg_down" 0)
    )     
  )
)


;ação para o botão "up"
(defun prt_cfglarg_up ()
  (setq larg_1 (fix (distof prt_cfglarg_sel));selecionado
	larg_2 (1- larg_1);subir
	counter 0
	new_list2 (list))
  (while (< counter (length prt_larg_list))
    (if (= counter larg_2)
      (progn
	(setq new_list2 (append new_list2 (list (nth (1+ counter) prt_larg_list))))
	(setq new_list2 (append new_list2 (list (nth counter prt_larg_list))))
	(setq counter (+ 2 counter))
      )
      (progn
	(setq new_list2 (append new_list2 (list (nth counter prt_larg_list))))
	(setq counter (1+ counter))
      )
    )
  )
  (setq prt_larg_list new_list2)
  (start_list "prt_cfglarg_list")
  (mapcar 'add_list prt_larg_list)
  (end_list)
  (setq prt_cfglarg_sel (rtos (1- (fix (distof prt_cfglarg_sel))) 2 0))
  (set_tile "prt_cfglarg_list" prt_cfglarg_sel)
  (cond
    ((= "0" prt_cfglarg_sel)
     (mode_tile "prt_cfglarg_up" 1)
     (mode_tile "prt_cfglarg_down" 0)
    )
    ((= prt_cfglarg_sel (rtos (1- larg_list_len) 2 0))
     (mode_tile "prt_cfglarg_up" 0)
     (mode_tile "prt_cfglarg_down" 1)
    )
    (t
     (mode_tile "prt_cfglarg_up" 0)
     (mode_tile "prt_cfglarg_down" 0)
    )     
  )
)

;ação para o botão "down"
(defun prt_cfglarg_down ()
  (setq larg_1 (fix (distof prt_cfglarg_sel));selecionado
	larg_2 (1+ larg_1);subir
	counter 0
	new_list2 (list))
  (while (< counter (length prt_larg_list))
    (if (= counter larg_1)
      (progn
	(setq new_list2 (append new_list2 (list (nth (1+ counter) prt_larg_list))))
	(setq new_list2 (append new_list2 (list (nth counter prt_larg_list))))
	(setq counter (+ 2 counter))
      )
      (progn
	(setq new_list2 (append new_list2 (list (nth counter prt_larg_list))))
	(setq counter (1+ counter))
      )
    )
  )
  (setq prt_larg_list new_list2)
  (start_list "prt_cfglarg_list")
  (mapcar 'add_list prt_larg_list)
  (end_list)
  (setq prt_cfglarg_sel (rtos (1+ (fix (distof prt_cfglarg_sel))) 2 0))
  (set_tile "prt_cfglarg_list" prt_cfglarg_sel)
  (cond
    ((= "0" prt_cfglarg_sel)
     (mode_tile "prt_cfglarg_up" 1)
     (mode_tile "prt_cfglarg_down" 0)
    )
    ((= prt_cfglarg_sel (rtos (1- larg_list_len) 2 0))
     (mode_tile "prt_cfglarg_up" 0)
     (mode_tile "prt_cfglarg_down" 1)
    )
    (t
     (mode_tile "prt_cfglarg_up" 0)
     (mode_tile "prt_cfglarg_down" 0)
    )     
  )
)



;***********************************
;Inicializações
;***********************************

;atualiza os 16 slides
(defun prt_update_slides ()
    ;atualiza as imagens
  (setq x (dimx_tile "icon11")
	y (dimy_tile "icon11"))
  (start_image "icon11")
  (slide_image 0 0 x y (strcat cnp_root "/slides/prt_11.sld"))
  (end_image)
  (setq x (dimx_tile "icon12")
	y (dimy_tile "icon12"))
  (start_image "icon12")
  (slide_image 0 0 x y (strcat cnp_root "/slides/prt_12.sld"))
  (end_image)
  (setq x (dimx_tile "icon13")
	y (dimy_tile "icon13"))
  (start_image "icon13")
  (slide_image 0 0 x y (strcat cnp_root "/slides/prt_13.sld"))
  (end_image)
  (setq x (dimx_tile "icon14")
	y (dimy_tile "icon14"))
  (start_image "icon14")
  (slide_image 0 0 x y (strcat cnp_root "/slides/prt_14.sld"))
  (end_image)
  (setq x (dimx_tile "icon21")
	y (dimy_tile "icon21"))
  (start_image "icon21")
  (slide_image 0 0 x y (strcat cnp_root "/slides/prt_21.sld"))
  (end_image)
  (setq x (dimx_tile "icon22")
	y (dimy_tile "icon22"))
  (start_image "icon22")
  (slide_image 0 0 x y (strcat cnp_root "/slides/prt_22.sld"))
  (end_image)
  (setq x (dimx_tile "icon23")
	y (dimy_tile "icon23"))
  (start_image "icon23")
  (slide_image 0 0 x y (strcat cnp_root "/slides/prt_23.sld"))
  (end_image)
  (setq x (dimx_tile "icon24")
	y (dimy_tile "icon24"))
  (start_image "icon24")
  (slide_image 0 0 x y (strcat cnp_root "/slides/prt_24.sld"))
  (end_image)
  (setq x (dimx_tile "icon31")
	y (dimy_tile "icon31"))
  (start_image "icon31")
  (slide_image 0 0 x y (strcat cnp_root "/slides/prt_31.sld"))
  (end_image)
  (setq x (dimx_tile "icon32")
	y (dimy_tile "icon32"))
  (start_image "icon32")
  (slide_image 0 0 x y (strcat cnp_root "/slides/prt_32.sld"))
  (end_image)
  (setq x (dimx_tile "icon33")
	y (dimy_tile "icon33"))
  (start_image "icon33")
  (slide_image 0 0 x y (strcat cnp_root "/slides/prt_33.sld"))
  (end_image)
  (setq x (dimx_tile "icon34")
	y (dimy_tile "icon34"))
  (start_image "icon34")
  (slide_image 0 0 x y (strcat cnp_root "/slides/prt_34.sld"))
  (end_image)
  (setq x (dimx_tile "icon41")
	y (dimy_tile "icon41"))
  (start_image "icon41")
  (slide_image 0 0 x y (strcat cnp_root "/slides/prt_41.sld"))
  (end_image)
  (setq x (dimx_tile "icon42")
	y (dimy_tile "icon42"))
  (start_image "icon42")
  (slide_image 0 0 x y (strcat cnp_root "/slides/prt_42.sld"))
  (end_image)
  (setq x (dimx_tile "icon43")
	y (dimy_tile "icon43"))
  (start_image "icon43")
  (slide_image 0 0 x y (strcat cnp_root "/slides/prt_43.sld"))
  (end_image)
  (setq x (dimx_tile "icon44")
	y (dimy_tile "icon44"))
  (start_image "icon44")
  (slide_image 0 0 x y (strcat cnp_root "/slides/prt_44.sld"))
  (end_image)
  (action_tile "icon11" "(prt_deftype)")
  (action_tile "icon12" "(prt_deftype)")
  (action_tile "icon13" "(prt_deftype)")
  (action_tile "icon14" "(prt_deftype)")
  (action_tile "icon21" "(prt_deftype)")
  (action_tile "icon22" "(prt_deftype)")
  (action_tile "icon23" "(prt_deftype)")
  (action_tile "icon24" "(prt_deftype)")
  (action_tile "icon31" "(prt_deftype)")
  (action_tile "icon32" "(prt_deftype)")
  (action_tile "icon33" "(prt_deftype)")
  (action_tile "icon34" "(prt_deftype)")
  (action_tile "icon41" "(prt_deftype)")
  (action_tile "icon42" "(prt_deftype)")
  (action_tile "icon43" "(prt_deftype)")
  (action_tile "icon44" "(prt_deftype)")
)

;ação ao escolher o typo de porta
(defun prt_deftype ()
  ;determina o tipo
  (setq prt_var_type $key
	prt_var_tipo (substr prt_var_type 5 2)
	x (dimx_tile "prt_slide_type")
	y (dimy_tile "prt_slide_type")
  )
  ;atualiza o slide
  (start_image "prt_slide_type")
  (fill_image 0 0 x y -2)
  (slide_image 0 0 x y (strcat cnp_root "/slides/prt_" prt_var_tipo ".sld"))
  (end_image)
  ;atualiza a lista de larguras
  (prt_larg_buildlista)
  ;lê os parâmetros do tipo de porta
)
  
;lê os dados iniciais da DCL no arquivo de dados
(defun prt_last_file ()
  (if (= prt_var_tipo nil ) (setq prt_var_tipo "11"))
  (if (= prt_var_larg nil ) (setq prt_var_larg "5"))
  (if (= prt_var_halt nil ) (setq prt_var_halt "0"))
  (if (= prt_var_posi nil ) (setq prt_var_posi "prt_afast"))
  (if (= prt_var_afas nil ) (setq prt_var_afas "5"))
  (if (= prt_var_wall nil ) (setq prt_var_wall "15"))
  (if (= prt_var_caix nil ) (setq prt_var_caix "2"))
  (if (= prt_var_iden nil ) (setq prt_var_iden "1"))
  (if (= prt_var_lrad nil ) (setq prt_var_lrad "prt_larg_radio1"))
  (if (= prt_var_lvao nil ) (setq prt_var_lvao "80"))
;;;  
;;;  (if (findfile (strcat cnp_root "/config/prt_last.txt"))
;;;    (prt_last_readfile)
;;;    (progn
;;;      (setq file (open (strcat cnp_root "/config/prt_last.txt") "w"))
;;;      (write-line "11" file)
;;;      (write-line "5" file)
;;;      (write-line "0" file)
;;;      (write-line "prt_afast" file)
;;;      (write-line "5" file)
;;;      (write-line "15" file)
;;;      (write-line "2" file)
;;;      (write-line "1" file)
;;;      (write-line "prt_larg_radio1" file)
;;;      (write-line "80" file)
;;;      (close file)
;;;      (prt_last_readfile)
;;;    )
;;;  )
)



;função que lê o arquivo de dados
(defun prt_last_readfile ()
  (if (= prt_var_tipo nil ) (setq prt_var_tipo "11"))
  (if (= prt_var_larg nil ) (setq prt_var_larg "5"))
  (if (= prt_var_halt nil ) (setq prt_var_halt "0"))
  (if (= prt_var_posi nil ) (setq prt_var_posi "prt_afast"))
  (if (= prt_var_afas nil ) (setq prt_var_afas "5"))
  (if (= prt_var_wall nil ) (setq prt_var_wall "15"))
  (if (= prt_var_caix nil ) (setq prt_var_caix "2"))
  (if (= prt_var_iden nil ) (setq prt_var_iden "1"))
  (if (= prt_var_lrad nil ) (setq prt_var_lrad "prt_larg_radio1"))
  (if (= prt_var_lvao nil ) (setq prt_var_lvao "80"))
;;;  (setq	file (open (strcat cnp_root "/config/prt_last.txt") "r"))
;;;  (setq	prt_var_tipo (read-line file))
;;;  (setq	prt_var_larg (read-line file))
;;;  (setq	prt_var_halt (read-line file))
;;;  (setq	prt_var_posi (read-line file))
;;;  (setq	prt_var_afas (read-line file))
;;;  (setq	prt_var_wall (read-line file))
;;;  (setq	prt_var_caix (read-line file))
;;;  (setq	prt_var_iden (read-line file))
;;;  (setq	prt_var_lrad (read-line file))
;;;  (setq	prt_var_lvao (read-line file))
;;;  (close file)
)

;função que escreve o arquivo de dados
;;;(defun prt_last_writefile ()
;;;  (setq	file (open (strcat cnp_root "/config/prt_last.txt") "w"))
;;;  (write-line prt_var_tipo file)
;;;  (write-line prt_var_larg file)
;;;  (write-line prt_var_halt file)
;;;  (write-line prt_var_posi file)
;;;  (write-line prt_var_afas file)
;;;  (write-line prt_var_wall file)
;;;  (write-line prt_var_caix file)
;;;  (write-line prt_var_iden file)
;;;  (write-line prt_var_lrad file)
;;;  (write-line prt_var_lvao file)
;;;  (close file)
;;;)

;*****************************************
;Abertura da parede                       
;*****************************************

;determina os pontos de 'break' das paredes
(defun prt_openfree (n)
  ;conversão de dados para numerais
  (prt_larg_file)
  (if (= prt_var_lrad "prt_larg_radio1")
    (setq prt_larg (* n prt_fator (distof (nth (fix (distof prt_var_larg)) prt_larg_list))))
    (setq prt_larg (* prt_fator (distof prt_var_lvao)))
  )
  (prt_halt_file)
  (setq prt_halt (* prt_fator (distof (nth (fix (distof prt_var_halt)) prt_halt_list)))
	prt_afas (* prt_fator (distof prt_var_afas))
	prt_wall (* prt_fator (distof prt_var_wall))
	prt_caix (* prt_fator (distof prt_var_caix))
  )
  ;clica na parede
  (prompt "\nSelecione a parede interna...")
  (setq prt_entsel (entsel)
	prt_ent1 (car prt_entsel)
	prt_ent1_type (cdr (assoc 0 (entget prt_ent1)))
	prt_pt0 (nth 0 (cdr prt_entsel))
	prt_ptt1 (cdr (assoc 10 (entget prt_ent1)))
	prt_ptt2 (cdr (assoc 11 (entget prt_ent1)))
	prt_wall_layer (cdr (assoc 8 (entget prt_ent1)))
  )
  (if (/= "LINE" prt_ent1_type)
    (progn
      (alert "A entidade Selecionada não é uma 'LINE'.\nPOLYLINES devem ser explodidas\npara usar este comando...")
      (prt_openfree 1)
    )
  )
  (if (<= (distance prt_pt0 prt_ptt1) (distance prt_pt0 prt_ptt2))
    (setq prt_pt1 prt_ptt1 prt_pt2 prt_ptt2 prt_code 1)
    (setq prt_pt1 prt_ptt2 prt_pt2 prt_ptt1 prt_code 2)
  )
  (setq prt_angbase (angle prt_pt1 prt_pt2))
  ;verifica o posicionamento para determinar os pontos de quebra
  (if (= prt_var_posi "prt_center")
    (setq prt_doll (/ (- (distance prt_pt1 prt_pt2) prt_larg (* 2 prt_caix)) 2))
    (setq prt_doll prt_afas)
  )
  (setq
	prt_brk1 (polar prt_pt1 prt_angbase prt_doll)
	prt_brk2 (polar prt_brk1 prt_angbase (+ prt_larg (* 2 prt_caix)))
  )
  (if (= prt_code 1)
    (setq prt_brk3a (polar prt_brk1 (- prt_angbase (/ pi 2)) prt_wall)
	  prt_brk3b (polar prt_brk1 (+ prt_angbase (/ pi 2)) prt_wall)
	  prt_brk4a (polar prt_brk2 (- prt_angbase (/ pi 2)) prt_wall)
	  prt_brk4b (polar prt_brk2 (+ prt_angbase (/ pi 2)) prt_wall)
    )
    (setq prt_brk3a (polar prt_brk1 (+ prt_angbase (/ pi 2)) prt_wall)
  	  prt_brk3b (polar prt_brk1 (- prt_angbase (/ pi 2)) prt_wall)
	  prt_brk4a (polar prt_brk2 (+ prt_angbase (/ pi 2)) prt_wall)
	  prt_brk4b (polar prt_brk2 (- prt_angbase (/ pi 2)) prt_wall)
    )
  )
  (if (/= nil (ssget "_f" (list prt_brk3a prt_brk4a) (list (cons 8 prt_wall_layer))))
    (progn
      (setq prt_brk3 prt_brk3a prt_brk4 prt_brk4a prt_xcode 1)
      (setq prt_brkm (polar prt_brk3 (angle prt_brk3 prt_brk4) (/ (distance prt_brk3 prt_brk4) 2)))
      (if (= nil (ssget "c" prt_brkm prt_brkm))
	(progn
	  (setq prt_brk3 prt_brk3b prt_brk4 prt_brk4b)
	  (setq prt_brkm (polar prt_brk3 (angle prt_brk3 prt_brk4) (/ (distance prt_brk3 prt_brk4) 2))
		prt_xcode 2)
	)
      )
    )
    (progn
      (setq prt_brk3 prt_brk3b prt_brk4 prt_brk4b prt_xcode 2)
      (setq prt_brkm (polar prt_brk3 (angle prt_brk3 prt_brk4) (/ (distance prt_brk3 prt_brk4) 2)))
      (if (= nil (ssget "c" prt_brkm prt_brkm))
	(progn
	  (setq prt_brk3 prt_brk3a prt_brk4 prt_brk4a)
	  (setq prt_brkm (polar prt_brk3 (angle prt_brk3 prt_brk4) (/ (distance prt_brk3 prt_brk4) 2))
		prt_xcode 4)
	)
      )
    )
  )
  (setq colmo (getvar "cecolor"))
  (command "._undo" "_m")
  (command "._break" prt_ent1 "_non" prt_brk1 "_non" prt_brk2)
  (command "._break" (ssget "c" prt_brkm prt_brkm) "_non" prt_brk3 "_non" prt_brk4)
  (command "._layer" "_s" prt_wall_layer "")
  (command "._line" "_non" prt_brk1 "_non" prt_brk3 "" "._line" "_non" prt_brk2 "_non" prt_brk4 "")
  (setq prt_angortho (angle prt_brk1 prt_brk3))
  (setq prt_mid1 (polar prt_brk1 prt_angbase (/ (distance prt_brk1 prt_brk2) 2.0))
	prt_mid2 (polar prt_brk3 prt_angbase (/ (distance prt_brk3 prt_brk4) 2.0))
  )
)



;***********************************
;Porta Tipo 11                      
;Parte 01 - Configuração            
;***********************************
(defun prt_cfg_11 ()
  (prt_pt11_file)
  (setq dcl_id (load_dialog (strcat cnp_root "/lisp/cadnorma.dcl")))
  (if (not (new_dialog "prt_cfg_p11" dcl_id)) (exit))
  (set_tile "prt_descr" "Porta Simples ('de Abrir')")
  ;slide de tipo
  (setq x (dimx_tile "prt_11_slide")
	y (dimy_tile "prt_11_slide")
  )
  (start_image "prt_11_slide")
  (fill_image 0 0 x y -2)
  (slide_image 0 0 x y (strcat cnp_root "/slides/prt_" prt_var_tipo ".sld"))
  (end_image)
  ;espessura da porta
  (set_tile "prt_11_poe_edit" prt_pt11_poe)
  (action_tile "prt_11_poe_edit" "(prt_11_poe_edit_act)")
  (action_tile "prt_11_poe_pick" "(done_dialog 2)")
  ;soleira
  (if (= "1" prt_pt11_soi) (set_tile "prt_11_solint"  "1"))
  (action_tile "prt_11_solint"  "(setq prt_pt11_soi $value)")
  (if (= "1" prt_pt11_soe) (set_tile "prt_11_solext"  "1"))
  (action_tile "prt_11_solext"  "(setq prt_pt11_soe $value)")
  ;alisares
  (if (= "1" prt_pt11_ali) (set_tile "prt_11_aliint"  "1"))
  (action_tile "prt_11_aliint"  "(setq prt_pt11_ali $value)")
  (if (= "1" prt_pt11_ale) (set_tile "prt_11_aliext"  "1"))
  (action_tile "prt_11_aliext"  "(setq prt_pt11_ale $value)")
  ;tipo de fechamento (arco, reta, nenhum)
  (setq x (dimx_tile "prt_11_arcsld_01")
	y (dimy_tile "prt_11_arcsld_01")
  )
  (start_image "prt_11_arcsld_01")
  (fill_image 0 0 x y -2)
  (slide_image 0 0 x y (strcat cnp_root "/slides/prt_arc_1101.sld"))
  (end_image)
  (setq x (dimx_tile "prt_11_arcsld_02")
	y (dimy_tile "prt_11_arcsld_02")
  )
  (start_image "prt_11_arcsld_02")
  (fill_image 0 0 x y -2)
  (slide_image 0 0 x y (strcat cnp_root "/slides/prt_arc_1102.sld"))
  (end_image)
  (setq x (dimx_tile "prt_11_arcsld_03")
	y (dimy_tile "prt_11_arcsld_03")
  )
  (start_image "prt_11_arcsld_03")
  (fill_image 0 0 x y -2)
  (slide_image 0 0 x y (strcat cnp_root "/slides/prt_arc_1103.sld"))
  (end_image)
  (action_tile "prt_11_arcsld_01" "(prt_11_arcsld_act)")
  (action_tile "prt_11_arcsld_02" "(prt_11_arcsld_act)")
  (action_tile "prt_11_arcsld_03" "(prt_11_arcsld_act)")
  (cond
    ((= prt_pt11_arc "prt_11_arc_01") (set_tile "prt_11_arc_01" "1"))
    ((= prt_pt11_arc "prt_11_arc_02") (set_tile "prt_11_arc_02" "1"))
    ((= prt_pt11_arc "prt_11_arc_03") (set_tile "prt_11_arc_03" "1"))
  )
  (action_tile "prt_11_arc_01" "(prt_11_arc_act)")
  (action_tile "prt_11_arc_02" "(prt_11_arc_act)")
  (action_tile "prt_11_arc_03" "(prt_11_arc_act)")
  ;tipo de caixilho
  (setq x (dimx_tile "prt_11_cxisld_01")
	y (dimy_tile "prt_11_cxisld_01")
  )
  (start_image "prt_11_cxisld_01")
  (fill_image 0 0 x y -2)
  (slide_image 0 0 x y (strcat cnp_root "/slides/prt_cxi_01.sld"))
  (end_image)
  (setq x (dimx_tile "prt_11_cxisld_02")
	y (dimy_tile "prt_11_cxisld_02")
  )
  (start_image "prt_11_cxisld_02")
  (fill_image 0 0 x y -2)
  (slide_image 0 0 x y (strcat cnp_root "/slides/prt_cxi_02.sld"))
  (end_image)
  (action_tile "prt_11_cxisld_01" "(prt_11_cxisld_act)")
  (action_tile "prt_11_cxisld_02" "(prt_11_cxisld_act)")
  (cond
    ((= prt_pt11_cxi "prt_11_cxi_01") (set_tile "prt_11_cxi_01" "1"))
    ((= prt_pt11_cxi "prt_11_cxi_02") (set_tile "prt_11_cxi_02" "1"))
  )
  (action_tile "prt_11_cxi_01" "(prt_11_cxi_act)")
  (action_tile "prt_11_cxi_02" "(prt_11_cxi_act)")
  ;tipo de maçaneta
  (setq x (dimx_tile "prt_11_macsld_01")
	y (dimy_tile "prt_11_macsld_01")
  )
  (start_image "prt_11_macsld_01")
  (fill_image 0 0 x y -2)
  (slide_image 0 0 x y (strcat cnp_root "/slides/prt_mac_01.sld"))
  (end_image)
  (setq x (dimx_tile "prt_11_macsld_02")
	y (dimy_tile "prt_11_macsld_02")
  )
  (start_image "prt_11_macsld_02")
  (fill_image 0 0 x y -2)
  (slide_image 0 0 x y (strcat cnp_root "/slides/prt_mac_02.sld"))
  (end_image)
  (setq x (dimx_tile "prt_11_macsld_03")
	y (dimy_tile "prt_11_macsld_03")
  )
  (start_image "prt_11_macsld_03")
  (fill_image 0 0 x y -2)
  (slide_image 0 0 x y (strcat cnp_root "/slides/prt_mac_03.sld"))
  (end_image)
  (setq x (dimx_tile "prt_11_macsld_04")
	y (dimy_tile "prt_11_macsld_04")
  )
  (start_image "prt_11_macsld_04")
  (fill_image 0 0 x y -2)
  (slide_image 0 0 x y (strcat cnp_root "/slides/prt_mac_04.sld"))
  (end_image)
  (setq x (dimx_tile "prt_11_macsld_05")
	y (dimy_tile "prt_11_macsld_05")
  )
  (start_image "prt_11_macsld_05")
  (fill_image 0 0 x y -2)
  (slide_image 0 0 x y (strcat cnp_root "/slides/prt_mac_05.sld"))
  (end_image)
  (action_tile "prt_11_macsld_01" "(prt_11_macsld_act)")
  (action_tile "prt_11_macsld_02" "(prt_11_macsld_act)")
  (action_tile "prt_11_macsld_03" "(prt_11_macsld_act)")
  (action_tile "prt_11_macsld_04" "(prt_11_macsld_act)")
  (action_tile "prt_11_macsld_05" "(prt_11_macsld_act)")
  (cond
    ((= prt_pt11_mac "prt_11_mac_01") (set_tile "prt_11_mac_01" "1"))
    ((= prt_pt11_mac "prt_11_mac_02") (set_tile "prt_11_mac_02" "1"))
    ((= prt_pt11_mac "prt_11_mac_03") (set_tile "prt_11_mac_03" "1"))
    ((= prt_pt11_mac "prt_11_mac_04") (set_tile "prt_11_mac_04" "1"))
    ((= prt_pt11_mac "prt_11_mac_05") (set_tile "prt_11_mac_05" "1"))
  )
  (action_tile "prt_11_mac_01" "(prt_11_mac_act)")
  (action_tile "prt_11_mac_02" "(prt_11_mac_act)")
  (action_tile "prt_11_mac_03" "(prt_11_mac_act)")
  (action_tile "prt_11_mac_04" "(prt_11_mac_act)")
  (action_tile "prt_11_mac_05" "(prt_11_mac_act)")
  ;ok_cancel
  (action_tile "cancel" "(done_dialog 0)")
  (action_tile "accept" "(done_dialog 1)")
  ;start_dialog
  (setq prt_11_id (start_dialog))
  (unload_dialog dcl_id)
  (if (= prt_11_id 1) (prt_pt11_writefile))
  (if (= prt_11_id 2) (prt_11_poe_button_act))
)

;radio_buttons para maçanetas
(defun prt_11_mac_act ()
  (setq prt_pt11_mac $key)
  (cond
    ((= prt_pt11_mac "prt_11_mac_01")
     (set_tile "prt_11_mac_01" "1")
     (set_tile "prt_11_mac_02" "0")
     (set_tile "prt_11_mac_03" "0")
     (set_tile "prt_11_mac_04" "0")
     (set_tile "prt_11_mac_05" "0")
    )
    ((= prt_pt11_mac "prt_11_mac_02")
     (set_tile "prt_11_mac_01" "0")
     (set_tile "prt_11_mac_02" "1")
     (set_tile "prt_11_mac_03" "0")
     (set_tile "prt_11_mac_04" "0")
     (set_tile "prt_11_mac_05" "0")
    )
    ((= prt_pt11_mac "prt_11_mac_03")
     (set_tile "prt_11_mac_01" "0")
     (set_tile "prt_11_mac_02" "0")
     (set_tile "prt_11_mac_03" "1")
     (set_tile "prt_11_mac_04" "0")
     (set_tile "prt_11_mac_05" "0")
    )
    ((= prt_pt11_mac "prt_11_mac_04")
     (set_tile "prt_11_mac_01" "0")
     (set_tile "prt_11_mac_02" "0")
     (set_tile "prt_11_mac_03" "0")
     (set_tile "prt_11_mac_04" "1")
     (set_tile "prt_11_mac_05" "0")
    )
    ((= prt_pt11_mac "prt_11_mac_05")
     (set_tile "prt_11_mac_01" "0")
     (set_tile "prt_11_mac_02" "0")
     (set_tile "prt_11_mac_03" "0")
     (set_tile "prt_11_mac_04" "0")
     (set_tile "prt_11_mac_05" "1")
    )
  )
)

;slides de tipo de maçaneta
(defun prt_11_macsld_act ()
  (setq prt_pt11_macsld $key)
  (cond
    ((= prt_pt11_macsld "prt_11_macsld_01")
     (setq prt_pt11_mac "prt_11_mac_01")
     (set_tile "prt_11_mac_01" "1")
     (set_tile "prt_11_mac_02" "0")
     (set_tile "prt_11_mac_03" "0")
     (set_tile "prt_11_mac_04" "0")
     (set_tile "prt_11_mac_05" "0")
    )
    ((= prt_pt11_macsld "prt_11_macsld_02")
     (setq prt_pt11_mac "prt_11_mac_02")
     (set_tile "prt_11_mac_01" "0")
     (set_tile "prt_11_mac_02" "1")
     (set_tile "prt_11_mac_03" "0")
     (set_tile "prt_11_mac_04" "0")
     (set_tile "prt_11_mac_05" "0")
    )
    ((= prt_pt11_macsld "prt_11_macsld_03")
     (setq prt_pt11_mac "prt_11_mac_03")
     (set_tile "prt_11_mac_01" "0")
     (set_tile "prt_11_mac_02" "0")
     (set_tile "prt_11_mac_03" "1")
     (set_tile "prt_11_mac_04" "0")
     (set_tile "prt_11_mac_05" "0")
    )
    ((= prt_pt11_macsld "prt_11_macsld_04")
     (setq prt_pt11_mac "prt_11_mac_04")
     (set_tile "prt_11_mac_01" "0")
     (set_tile "prt_11_mac_02" "0")
     (set_tile "prt_11_mac_03" "0")
     (set_tile "prt_11_mac_04" "1")
     (set_tile "prt_11_mac_05" "0")
    )
    ((= prt_pt11_macsld "prt_11_macsld_05")
     (setq prt_pt11_mac "prt_11_mac_05")
     (set_tile "prt_11_mac_01" "0")
     (set_tile "prt_11_mac_02" "0")
     (set_tile "prt_11_mac_03" "0")
     (set_tile "prt_11_mac_04" "0")
     (set_tile "prt_11_mac_05" "1")
    )
  )
)


;radio_buttons para caixilho
(defun prt_11_cxi_act ()
  (setq prt_pt11_cxi $key)
  (cond
    ((= prt_pt11_cxi "prt_11_cxi_01")
     (set_tile "prt_11_cxi_01" "1")
     (set_tile "prt_11_cxi_02" "0")
    )
    ((= prt_pt11_cxi "prt_11_cxi_02")
     (set_tile "prt_11_cxi_01" "0")
     (set_tile "prt_11_cxi_02" "1")
    )
  )
)


;slides de tipo de caixilho
(defun prt_11_cxisld_act ()
  (setq prt_pt11_cxisld $key)
  (cond
    ((= prt_pt11_cxisld "prt_11_cxisld_01")
     (setq prt_pt11_cxi "prt_11_cxi_01")
     (set_tile "prt_11_cxi_01" "1")
     (set_tile "prt_11_cxi_02" "0")
     (set_tile "prt_11_cxi_03" "0")
    )
    ((= prt_pt11_cxisld "prt_11_cxisld_02")
     (setq prt_pt11_cxi "prt_11_cxi_02")
     (set_tile "prt_11_cxi_01" "0")
     (set_tile "prt_11_cxi_02" "1")
     (set_tile "prt_11_cxi_03" "0")
    )
    ((= prt_pt11_cxisld "prt_11_cxisld_03")
     (setq prt_pt11_cxi "prt_11_cxi_03")
     (set_tile "prt_11_cxi_01" "0")
     (set_tile "prt_11_cxi_02" "0")
     (set_tile "prt_11_cxi_03" "1")
    )
  )
)

;radio_buttons para fechamento
(defun prt_11_arc_act ()
  (setq prt_pt11_arc $key)
  (cond
    ((= prt_pt11_arc "prt_11_arc_01")
     (set_tile "prt_11_arc_01" "1")
     (set_tile "prt_11_arc_02" "0")
     (set_tile "prt_11_arc_03" "0")
    )
    ((= prt_pt11_arc "prt_11_arc_02")
     (set_tile "prt_11_arc_01" "0")
     (set_tile "prt_11_arc_02" "1")
     (set_tile "prt_11_arc_03" "0")
    )
    ((= prt_pt11_arc "prt_11_arc_03")
     (set_tile "prt_11_arc_01" "0")
     (set_tile "prt_11_arc_02" "0")
     (set_tile "prt_11_arc_03" "1")
    )
  )
)

;slides de tipo de arco
(defun prt_11_arcsld_act ()
  (setq prt_pt11_arcsld $key)
  (cond
    ((= prt_pt11_arcsld "prt_11_arcsld_01")
     (setq prt_pt11_arc "prt_11_arc_01")
     (set_tile "prt_11_arc_01" "1")
     (set_tile "prt_11_arc_02" "0")
     (set_tile "prt_11_arc_03" "0")
    )
    ((= prt_pt11_arcsld "prt_11_arcsld_02")
     (setq prt_pt11_arc "prt_11_arc_02")
     (set_tile "prt_11_arc_01" "0")
     (set_tile "prt_11_arc_02" "1")
     (set_tile "prt_11_arc_03" "0")
    )
    ((= prt_pt11_arcsld "prt_11_arcsld_03")
     (setq prt_pt11_arc "prt_11_arc_03")
     (set_tile "prt_11_arc_01" "0")
     (set_tile "prt_11_arc_02" "0")
     (set_tile "prt_11_arc_03" "1")
    )
  )
)


;Espessura por Pick Points
(defun prt_11_poe_button_act ()
  (prt_pt11_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt11_poe (rtos new_dist 2 2))
      (prt_pt11_writefile)
    )
  )
  (prt_cfg_11)
)


;verifica se o valor de espessura entrado é válido
(defun prt_11_poe_edit_act ()
  (setq prt_var_newpoe $value)
  (if (distof prt_var_newpoe)
    (progn
      (setq prt_pt11_poe prt_var_newpoe)
      (prt_pt11_writefile)
    )
    (progn
      (alert "Valor Inválido!")
      (set_tile "prt_11_poe_edit" prt_pt11_poe)
      (mode_tile "prt_11_poe_edit" 2)
    )
  )
)  

;lê os dados iniciais da DCL no arquivo de dados
(defun prt_pt11_file ()
  (if (findfile (strcat cnp_root "/config/prt_pt11.txt"))
    (prt_pt11_readfile)
    (progn
      (setq file (open (strcat cnp_root "/config/prt_pt11.txt") "w" "utf8"))
      (write-line "3" file)
      (write-line "1" file)
      (write-line "1" file)      
      (write-line "1" file)
      (write-line "1" file)
      (write-line "prt_11_arc_01" file)
      (write-line "prt_11_cxi_01" file)
      (write-line "prt_11_mac_01" file)
      (close file)
      (prt_pt11_readfile)
    )
  )
)


;função que lê o arquivo de dados
(defun prt_pt11_readfile ()
  (setq	file (open (strcat cnp_root "/config/prt_pt11.txt") "r" "utf8"))
  (setq	prt_pt11_poe (read-line file))
  (setq	prt_pt11_soi (read-line file))
  (setq	prt_pt11_soe (read-line file))
  (setq	prt_pt11_ali (read-line file))
  (setq	prt_pt11_ale (read-line file))
  (setq	prt_pt11_arc (read-line file))
  (setq	prt_pt11_cxi (read-line file))
  (setq	prt_pt11_mac (read-line file))
  (close file)
)

;função que escreve o arquivo de dados
(defun prt_pt11_writefile ()
  (setq	file (open (strcat cnp_root "/config/prt_pt11.txt") "w" "utf8"))
  (write-line prt_pt11_poe file)
  (write-line prt_pt11_soi file)
  (write-line prt_pt11_soe file)
  (write-line prt_pt11_ali file)
  (write-line prt_pt11_ale file)
  (write-line prt_pt11_arc file)
  (write-line prt_pt11_cxi file)
  (write-line prt_pt11_mac file)
  (close file)
)

;Desenha a porta

(defun prt_drw11 ()
  (cn7_init)
  (guarda '("blipmode" "cecolor" "celtype" "clayer" "cmdecho" "orthomode"
          "textstyle" "luprec" "osmode" ))
  (setvar "cecolor" "bylayer")
  (prt_pt11_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 1.0)
  ;desenha o caixilho, se houver
  (prt_drw11_caixilho)
  (prt_drw11_porta)
  (prt_drw11_arco)
  (if (/= prt_pt11_mac "prt_11_mac_05")
    (prt_drw11_maçaneta)
  )
  (prt_drw11_soleira)
  (if (/= 0.0 prt_caix)
    (prt_drw11_alisar)
  )
  (devolve)
  (prompt "\nUse o comando <UB> para retornar... ")
)


;*****************************************
;Desenho das Alisares                     
;*****************************************
(defun prt_drw11_alisar ()
  (cn7_verylayer prt_layc_all 7)
  (setvar "cecolor" prt_layc_alc)
  ;internos
  (if (= "1" prt_pt11_ali)
    (progn
      (if (= prt_pt11_cxi "prt_11_cxi_01")
	(setq prt_ali_b1 (polar prt_cxi2 prt_angbase (* 1.0 prt_fator)))
	(setq prt_ali_b1 (polar prt_cxi5 prt_angbase (* 1.0 prt_fator)))
      )
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt11_ale)
    (progn
      (if (= prt_pt11_cxi "prt_11_cxi_01")
	(progn
	  (setq prt_ale_a1 (polar prt_cxi3 (+ prt_angbase pi) (* 1.0 prt_fator)))
	  (setq prt_ale_b1 (polar prt_cxi4 prt_angbase (* 1.0 prt_fator)))
	)
	(progn
	  (setq prt_ale_a1 (polar prt_cxi4 (+ prt_angbase pi) (* 1.0 prt_fator)))
	  (setq prt_ale_b1 (polar prt_cxi8 prt_angbase (* 1.0 prt_fator)))
	)
      )
      (setq prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw11_soleira ()
  (cn7_verylayer prt_layc_sol 7)
  (setvar "cecolor" prt_layc_soc)
  (if (= prt_pt11_soi "1")
    (if (= prt_pt11_cxi "prt_11_cxi_01")
;;;      (command "._line" "_non" prt_porta2 "_non" prt_cxi2 "")
;;;      (command "._line" "_non" prt_porta2 "_non" prt_cxi5 "")
      (command "._line" "_non" prt_cxi1 "_non" prt_cxi2 "")
      (command "._line" "_non" prt_cxi1 "_non" prt_cxi5 "")
    )
  )
  (if (= prt_pt11_soe "1")
    (if (= prt_pt11_cxi "prt_11_cxi_01")
      (command "._line" "_non" prt_cxi3 "_non" prt_cxi4 "")
      (command "._line" "_non" prt_cxi4 "_non" prt_cxi8 "")
    )
  )
)


;*****************************************
;Desenho das Maçanetas                    
;*****************************************
(defun prt_drw11_maçaneta ()
  (setq prt_mac1 (polar prt_porta4 prt_angortho (* 7.0 prt_fator))
	prt_mac2 (polar prt_porta3 prt_angortho (* 7.0 prt_fator))
  )
  (cond
    ((= prt_pt11_mac "prt_11_mac_01") (setq prt_mac_blk "prt_mac01"))
    ((= prt_pt11_mac "prt_11_mac_02") (setq prt_mac_blk "prt_mac02"))
    ((= prt_pt11_mac "prt_11_mac_03") (setq prt_mac_blk "prt_mac03"))
    ((= prt_pt11_mac "prt_11_mac_04") (setq prt_mac_blk "prt_mac04"))
  )
  (cn7_verylayer prt_layc_mal 7)
  (setvar "cecolor" prt_layc_poc)
  (if (= prt_code 1)
    (cond
      ((or (= prt_xcode 1) (= prt_xcode 3) (= prt_xcode 4))
       (command "._insert" (strcat cnp_root "/blocos/" prt_mac_blk "a.dwg") "_non" prt_mac1 prt_blkscl prt_blkscl "_non" prt_porta4
		"._explode" (entlast) "._chprop" "_p" "" "_p" "_c" prt_layc_mac "_la" prt_layc_mal "")
       (command "._insert" (strcat cnp_root "/blocos/" prt_mac_blk "b.dwg") "_non" prt_mac2 prt_blkscl prt_blkscl "_non" prt_porta3
		"._explode" (entlast) "._chprop" "_p" "" "_p" "_c" prt_layc_mac "_la" prt_layc_mal "")
      )
      ((= prt_xcode 2)
       (command "._insert" (strcat cnp_root "/blocos/" prt_mac_blk "a.dwg") "_non" prt_mac1 prt_blkscl (- prt_blkscl) "_non" prt_porta4
		"._explode" (entlast) "._chprop" "_p" "" "_p" "_c" prt_layc_mac "_la" prt_layc_mal "")
       (command "._insert" (strcat cnp_root "/blocos/" prt_mac_blk "b.dwg") "_non" prt_mac2 prt_blkscl (- prt_blkscl) "_non" prt_porta3
		"._explode" (entlast) "._chprop" "_p" "" "_p" "_c" prt_layc_mac "_la" prt_layc_mal "")
      )
    )
    (cond
      ((or (= prt_xcode 1) (= prt_xcode 4))
       (command "._insert" (strcat cnp_root "/blocos/" prt_mac_blk "a.dwg") "_non" prt_mac1 prt_blkscl (- prt_blkscl) "_non" prt_porta4
		"._explode" (entlast) "._chprop" "_p" "" "_p" "_c" prt_layc_mac "_la" prt_layc_mal "")
       (command "._insert" (strcat cnp_root "/blocos/" prt_mac_blk "b.dwg") "_non" prt_mac2 prt_blkscl (- prt_blkscl) "_non" prt_porta3
		"._explode" (entlast) "._chprop" "_p" "" "_p" "_c" prt_layc_mac "_la" prt_layc_mal "")
      )
      ((or (= prt_xcode 2) (= prt_xcode 3))
       (command "._insert" (strcat cnp_root "/blocos/" prt_mac_blk "a.dwg") "_non" prt_mac1 prt_blkscl prt_blkscl "_non" prt_porta4
		"._explode" (entlast) "._chprop" "_p" "" "_p" "_c" prt_layc_mac "_la" prt_layc_mal "")
       (command "._insert" (strcat cnp_root "/blocos/" prt_mac_blk "b.dwg") "_non" prt_mac2 prt_blkscl prt_blkscl "_non" prt_porta3
		"._explode" (entlast) "._chprop" "_p" "" "_p" "_c" prt_layc_mac "_la" prt_layc_mal "")
      )
    )
  )
)

;*****************************************
;Desenho de Arcos                         
;*****************************************
(defun prt_drw11_arco ()
  (cn7_verylayer prt_layc_arl 7)
  (setvar "cecolor" prt_layc_arc)
  (cond
    ((= prt_pt11_arc "prt_11_arc_01")
     (setq prt_arctang (polar prt_arcstart (+ prt_angortho pi) prt_larg))
     (command "._arc" "_non" prt_arcstart "_e" "_non" prt_porta3 "_d" "_non" prt_arctang)
    )
    ((= prt_pt11_arc "prt_11_arc_02")
     (command "._line" "_non" prt_arcstart "_non" prt_porta3 "")
    )
   )
)


;*****************************************
;Desenho de Portas                        
;*****************************************
(defun prt_drw11_porta ()
  (setq prt_porta2 (polar prt_porta1 prt_angbase (* prt_fator (distof prt_pt11_poe)))
	prt_porta3 (polar prt_porta2 (+ prt_angortho pi) prt_larg)
	prt_porta4 (polar prt_porta1 (+ prt_angortho pi) prt_larg)
  )
  (cn7_verylayer prt_layc_pol 7)
  (setvar "cecolor" prt_layc_poc)
  (command "._pline"  "_non" prt_porta1 "_non" prt_porta2  "_non" prt_porta3 "_non" prt_porta4 "_c")
)


;*****************************************
;Desenho de Caixilho                      
;*****************************************

;desenha os caixihos
(defun prt_drw11_caixilho ()
  (cn7_verylayer prt_layc_cxl 7)
  (setvar "cecolor" prt_layc_cxc)
  (if (/= 0.0 prt_caix)
    (progn
      (if (= prt_pt11_cxi "prt_11_cxi_01")
	(progn
	  (setq prt_cxi1 (polar prt_brk1 prt_angbase prt_caix)
		prt_cxi2 (polar prt_cxi1 prt_angbase prt_larg)
		prt_cxi3 (polar prt_brk3 prt_angbase prt_caix)
		prt_cxi4 (polar prt_cxi3 prt_angbase prt_larg)
		)
	  (command "._pline"  "_non" prt_brk1 "_non" prt_cxi1  "_non" prt_cxi3 "_non" prt_brk3 "" ;"_c"
		   "._pline"  "_non" prt_brk2 "_non" prt_cxi2  "_non" prt_cxi4 "_non" prt_brk4 "" ;"_c"
          )
	  (setq prt_arcstart prt_cxi2)
	)
	(progn
	  (setq prt_cxi1 (polar prt_brk1 prt_angbase prt_caix)
		prt_cxi2 (polar prt_cxi1 prt_angortho (* prt_fator (distof prt_pt11_poe)) )
		prt_cxi3 (polar prt_cxi2 prt_angbase (* prt_fator 2.0))
		prt_cxi4 (polar prt_brk3 prt_angbase (+ prt_caix (* prt_fator 2.0)))
		)
	  (command "._pline"  "_non" prt_brk1 "_non" prt_cxi1  "_non" prt_cxi2 "_non" prt_cxi3 "_non" prt_cxi4 "_non" prt_brk3 "");"_c")
	  (setq prt_cxi5 (polar prt_cxi1 prt_angbase prt_larg)
		prt_cxi6 (polar prt_cxi5 prt_angortho (* prt_fator (distof prt_pt11_poe)))
		prt_cxi7 (polar prt_cxi6 (+ pi prt_angbase) (* prt_fator 2.0))
		prt_cxi8 (polar prt_brk4 (+ pi prt_angbase) (+ prt_caix (* prt_fator 2.0)))
		)
	  (command "._pline"  "_non" prt_brk2 "_non" prt_cxi5  "_non" prt_cxi6 "_non" prt_cxi7 "_non" prt_cxi8 "_non" prt_brk4 "");"_c")
	  (setq prt_arcstart prt_cxi5)
        )
      )
      (setq prt_porta1 prt_cxi1)
    )
    ;se o caixilho for nulo
    (progn
      (setq prt_cxi1 prt_brk1
	    prt_cxi2 prt_brk2
	    prt_cxi3 prt_brk3
	    prt_cxi5 prt_brk2
	    prt_cxi8 prt_brk4
	    prt_arcstart prt_cxi2
	    prt_porta1 prt_cxi1
      )
      (if (= prt_pt11_cxi "prt_11_cxi_01")
	(setq prt_cxi4 prt_brk4)
	(setq prt_cxi4 prt_brk3)
      )
    )
  )
)


;***********************************
;Porta Tipo 12                      
;Parte 01 - Configuração            
;***********************************
(defun prt_cfg_12 ()
  (prt_pt12_file)
  (setq dcl_id (load_dialog (strcat cnp_root "/lisp/cadnorma.dcl")))
  (if (not (new_dialog "prt_cfg_p12" dcl_id)) (exit))
  (set_tile "prt_descr" "Porta Dupla ('de Abrir')")
  ;slide de tipo
  (setq x (dimx_tile "prt_12_slide")
	y (dimy_tile "prt_12_slide")
  )
  (start_image "prt_12_slide")
  (fill_image 0 0 x y -2)
  (slide_image 0 0 x y (strcat cnp_root "/slides/prt_" prt_var_tipo ".sld"))
  (end_image)
  ;espessura da porta
  (set_tile "prt_12_poe_edit" prt_pt12_poe)
  (action_tile "prt_12_poe_edit" "(prt_12_poe_edit_act)")
  (action_tile "prt_12_poe_pick" "(done_dialog 2)")
  ;soleira
  (if (= "1" prt_pt12_soi) (set_tile "prt_12_solint"  "1"))
  (action_tile "prt_12_solint"  "(setq prt_pt12_soi $value)")
  (if (= "1" prt_pt12_soe) (set_tile "prt_12_solext"  "1"))
  (action_tile "prt_12_solext"  "(setq prt_pt12_soe $value)")
  ;alisares
  (if (= "1" prt_pt12_ali) (set_tile "prt_12_aliint"  "1"))
  (action_tile "prt_12_aliint"  "(setq prt_pt12_ali $value)")
  (if (= "1" prt_pt12_ale) (set_tile "prt_12_aliext"  "1"))
  (action_tile "prt_12_aliext"  "(setq prt_pt12_ale $value)")
  ;tipo de fechamento (arco, reta, nenhum)
  (setq x (dimx_tile "prt_12_arcsld_01")
	y (dimy_tile "prt_12_arcsld_01")
  )
  (start_image "prt_12_arcsld_01")
  (fill_image 0 0 x y -2)
  (slide_image 0 0 x y (strcat cnp_root "/slides/prt_arc_1201.sld"))
  (end_image)
  (setq x (dimx_tile "prt_12_arcsld_02")
	y (dimy_tile "prt_12_arcsld_02")
  )
  (start_image "prt_12_arcsld_02")
  (fill_image 0 0 x y -2)
  (slide_image 0 0 x y (strcat cnp_root "/slides/prt_arc_1202.sld"))
  (end_image)
  (setq x (dimx_tile "prt_12_arcsld_03")
	y (dimy_tile "prt_12_arcsld_03")
  )
  (start_image "prt_12_arcsld_03")
  (fill_image 0 0 x y -2)
  (slide_image 0 0 x y (strcat cnp_root "/slides/prt_arc_1203.sld"))
  (end_image)
  (action_tile "prt_12_arcsld_01" "(prt_12_arcsld_act)")
  (action_tile "prt_12_arcsld_02" "(prt_12_arcsld_act)")
  (action_tile "prt_12_arcsld_03" "(prt_12_arcsld_act)")
  (cond
    ((= prt_pt12_arc "prt_12_arc_01") (set_tile "prt_12_arc_01" "1"))
    ((= prt_pt12_arc "prt_12_arc_02") (set_tile "prt_12_arc_02" "1"))
    ((= prt_pt12_arc "prt_12_arc_03") (set_tile "prt_12_arc_03" "1"))
  )
  (action_tile "prt_12_arc_01" "(prt_12_arc_act)")
  (action_tile "prt_12_arc_02" "(prt_12_arc_act)")
  (action_tile "prt_12_arc_03" "(prt_12_arc_act)")
  ;tipo de caixilho
  (setq x (dimx_tile "prt_12_cxisld_01")
	y (dimy_tile "prt_12_cxisld_01")
  )
  (start_image "prt_12_cxisld_01")
  (fill_image 0 0 x y -2)
  (slide_image 0 0 x y (strcat cnp_root "/slides/prt_cxi_01.sld"))
  (end_image)
  (setq x (dimx_tile "prt_12_cxisld_02")
	y (dimy_tile "prt_12_cxisld_02")
  )
  (start_image "prt_12_cxisld_02")
  (fill_image 0 0 x y -2)
  (slide_image 0 0 x y (strcat cnp_root "/slides/prt_cxi_02.sld"))
  (end_image)
  (action_tile "prt_12_cxisld_01" "(prt_12_cxisld_act)")
  (action_tile "prt_12_cxisld_02" "(prt_12_cxisld_act)")
  (cond
    ((= prt_pt12_cxi "prt_12_cxi_01") (set_tile "prt_12_cxi_01" "1"))
    ((= prt_pt12_cxi "prt_12_cxi_02") (set_tile "prt_12_cxi_02" "1"))
  )
  (action_tile "prt_12_cxi_01" "(prt_12_cxi_act)")
  (action_tile "prt_12_cxi_02" "(prt_12_cxi_act)")
  ;tipo de maçaneta
  (setq x (dimx_tile "prt_12_macsld_01")
	y (dimy_tile "prt_12_macsld_01")
  )
  (start_image "prt_12_macsld_01")
  (fill_image 0 0 x y -2)
  (slide_image 0 0 x y (strcat cnp_root "/slides/prt_mac_01.sld"))
  (end_image)
  (setq x (dimx_tile "prt_12_macsld_02")
	y (dimy_tile "prt_12_macsld_02")
  )
  (start_image "prt_12_macsld_02")
  (fill_image 0 0 x y -2)
  (slide_image 0 0 x y (strcat cnp_root "/slides/prt_mac_02.sld"))
  (end_image)
  (setq x (dimx_tile "prt_12_macsld_03")
	y (dimy_tile "prt_12_macsld_03")
  )
  (start_image "prt_12_macsld_03")
  (fill_image 0 0 x y -2)
  (slide_image 0 0 x y (strcat cnp_root "/slides/prt_mac_03.sld"))
  (end_image)
  (setq x (dimx_tile "prt_12_macsld_04")
	y (dimy_tile "prt_12_macsld_04")
  )
  (start_image "prt_12_macsld_04")
  (fill_image 0 0 x y -2)
  (slide_image 0 0 x y (strcat cnp_root "/slides/prt_mac_04.sld"))
  (end_image)
  (setq x (dimx_tile "prt_12_macsld_05")
	y (dimy_tile "prt_12_macsld_05")
  )
  (start_image "prt_12_macsld_05")
  (fill_image 0 0 x y -2)
  (slide_image 0 0 x y (strcat cnp_root "/slides/prt_mac_05.sld"))
  (end_image)
  (action_tile "prt_12_macsld_01" "(prt_12_macsld_act)")
  (action_tile "prt_12_macsld_02" "(prt_12_macsld_act)")
  (action_tile "prt_12_macsld_03" "(prt_12_macsld_act)")
  (action_tile "prt_12_macsld_04" "(prt_12_macsld_act)")
  (action_tile "prt_12_macsld_05" "(prt_12_macsld_act)")
  (cond
    ((= prt_pt12_mac "prt_12_mac_01") (set_tile "prt_12_mac_01" "1"))
    ((= prt_pt12_mac "prt_12_mac_02") (set_tile "prt_12_mac_02" "1"))
    ((= prt_pt12_mac "prt_12_mac_03") (set_tile "prt_12_mac_03" "1"))
    ((= prt_pt12_mac "prt_12_mac_04") (set_tile "prt_12_mac_04" "1"))
    ((= prt_pt12_mac "prt_12_mac_05") (set_tile "prt_12_mac_05" "1"))
  )
  (action_tile "prt_12_mac_01" "(prt_12_mac_act)")
  (action_tile "prt_12_mac_02" "(prt_12_mac_act)")
  (action_tile "prt_12_mac_03" "(prt_12_mac_act)")
  (action_tile "prt_12_mac_04" "(prt_12_mac_act)")
  (action_tile "prt_12_mac_05" "(prt_12_mac_act)")
  ;ok_cancel
  (action_tile "cancel" "(done_dialog 0)")
  (action_tile "accept" "(done_dialog 1)")
  ;start_dialog
  (setq prt_12_id (start_dialog))
  (unload_dialog dcl_id)
  (if (= prt_12_id 1) (prt_pt12_writefile))
  (if (= prt_12_id 2) (prt_12_poe_button_act))
)

;radio_buttons para maçanetas
(defun prt_12_mac_act ()
  (setq prt_pt12_mac $key)
  (cond
    ((= prt_pt12_mac "prt_12_mac_01")
     (set_tile "prt_12_mac_01" "1")
     (set_tile "prt_12_mac_02" "0")
     (set_tile "prt_12_mac_03" "0")
     (set_tile "prt_12_mac_04" "0")
     (set_tile "prt_12_mac_05" "0")
    )
    ((= prt_pt12_mac "prt_12_mac_02")
     (set_tile "prt_12_mac_01" "0")
     (set_tile "prt_12_mac_02" "1")
     (set_tile "prt_12_mac_03" "0")
     (set_tile "prt_12_mac_04" "0")
     (set_tile "prt_12_mac_05" "0")
    )
    ((= prt_pt12_mac "prt_12_mac_03")
     (set_tile "prt_12_mac_01" "0")
     (set_tile "prt_12_mac_02" "0")
     (set_tile "prt_12_mac_03" "1")
     (set_tile "prt_12_mac_04" "0")
     (set_tile "prt_12_mac_05" "0")
    )
    ((= prt_pt12_mac "prt_12_mac_04")
     (set_tile "prt_12_mac_01" "0")
     (set_tile "prt_12_mac_02" "0")
     (set_tile "prt_12_mac_03" "0")
     (set_tile "prt_12_mac_04" "1")
     (set_tile "prt_12_mac_05" "0")
    )
    ((= prt_pt12_mac "prt_12_mac_05")
     (set_tile "prt_12_mac_01" "0")
     (set_tile "prt_12_mac_02" "0")
     (set_tile "prt_12_mac_03" "0")
     (set_tile "prt_12_mac_04" "0")
     (set_tile "prt_12_mac_05" "1")
    )
  )
)

;slides de tipo de maçaneta
(defun prt_12_macsld_act ()
  (setq prt_pt12_macsld $key)
  (cond
    ((= prt_pt12_macsld "prt_12_macsld_01")
     (setq prt_pt12_mac "prt_12_mac_01")
     (set_tile "prt_12_mac_01" "1")
     (set_tile "prt_12_mac_02" "0")
     (set_tile "prt_12_mac_03" "0")
     (set_tile "prt_12_mac_04" "0")
     (set_tile "prt_12_mac_05" "0")
    )
    ((= prt_pt12_macsld "prt_12_macsld_02")
     (setq prt_pt12_mac "prt_12_mac_02")
     (set_tile "prt_12_mac_01" "0")
     (set_tile "prt_12_mac_02" "1")
     (set_tile "prt_12_mac_03" "0")
     (set_tile "prt_12_mac_04" "0")
     (set_tile "prt_12_mac_05" "0")
    )
    ((= prt_pt12_macsld "prt_12_macsld_03")
     (setq prt_pt12_mac "prt_12_mac_03")
     (set_tile "prt_12_mac_01" "0")
     (set_tile "prt_12_mac_02" "0")
     (set_tile "prt_12_mac_03" "1")
     (set_tile "prt_12_mac_04" "0")
     (set_tile "prt_12_mac_05" "0")
    )
    ((= prt_pt12_macsld "prt_12_macsld_04")
     (setq prt_pt12_mac "prt_12_mac_04")
     (set_tile "prt_12_mac_01" "0")
     (set_tile "prt_12_mac_02" "0")
     (set_tile "prt_12_mac_03" "0")
     (set_tile "prt_12_mac_04" "1")
     (set_tile "prt_12_mac_05" "0")
    )
    ((= prt_pt12_macsld "prt_12_macsld_05")
     (setq prt_pt12_mac "prt_12_mac_05")
     (set_tile "prt_12_mac_01" "0")
     (set_tile "prt_12_mac_02" "0")
     (set_tile "prt_12_mac_03" "0")
     (set_tile "prt_12_mac_04" "0")
     (set_tile "prt_12_mac_05" "1")
    )
  )
)


;radio_buttons para caixilho
(defun prt_12_cxi_act ()
  (setq prt_pt12_cxi $key)
  (cond
    ((= prt_pt12_cxi "prt_12_cxi_01")
     (set_tile "prt_12_cxi_01" "1")
     (set_tile "prt_12_cxi_02" "0")
    )
    ((= prt_pt12_cxi "prt_12_cxi_02")
     (set_tile "prt_12_cxi_01" "0")
     (set_tile "prt_12_cxi_02" "1")
    )
  )
)


;slides de tipo de caixilho
(defun prt_12_cxisld_act ()
  (setq prt_pt12_cxisld $key)
  (cond
    ((= prt_pt12_cxisld "prt_12_cxisld_01")
     (setq prt_pt12_cxi "prt_12_cxi_01")
     (set_tile "prt_12_cxi_01" "1")
     (set_tile "prt_12_cxi_02" "0")
     (set_tile "prt_12_cxi_03" "0")
    )
    ((= prt_pt12_cxisld "prt_12_cxisld_02")
     (setq prt_pt12_cxi "prt_12_cxi_02")
     (set_tile "prt_12_cxi_01" "0")
     (set_tile "prt_12_cxi_02" "1")
     (set_tile "prt_12_cxi_03" "0")
    )
    ((= prt_pt12_cxisld "prt_12_cxisld_03")
     (setq prt_pt12_cxi "prt_12_cxi_03")
     (set_tile "prt_12_cxi_01" "0")
     (set_tile "prt_12_cxi_02" "0")
     (set_tile "prt_12_cxi_03" "1")
    )
  )
)

;radio_buttons para fechamento
(defun prt_12_arc_act ()
  (setq prt_pt12_arc $key)
  (cond
    ((= prt_pt12_arc "prt_12_arc_01")
     (set_tile "prt_12_arc_01" "1")
     (set_tile "prt_12_arc_02" "0")
     (set_tile "prt_12_arc_03" "0")
    )
    ((= prt_pt12_arc "prt_12_arc_02")
     (set_tile "prt_12_arc_01" "0")
     (set_tile "prt_12_arc_02" "1")
     (set_tile "prt_12_arc_03" "0")
    )
    ((= prt_pt12_arc "prt_12_arc_03")
     (set_tile "prt_12_arc_01" "0")
     (set_tile "prt_12_arc_02" "0")
     (set_tile "prt_12_arc_03" "1")
    )
  )
)

;slides de tipo de arco
(defun prt_12_arcsld_act ()
  (setq prt_pt12_arcsld $key)
  (cond
    ((= prt_pt12_arcsld "prt_12_arcsld_01")
     (setq prt_pt12_arc "prt_12_arc_01")
     (set_tile "prt_12_arc_01" "1")
     (set_tile "prt_12_arc_02" "0")
     (set_tile "prt_12_arc_03" "0")
    )
    ((= prt_pt12_arcsld "prt_12_arcsld_02")
     (setq prt_pt12_arc "prt_12_arc_02")
     (set_tile "prt_12_arc_01" "0")
     (set_tile "prt_12_arc_02" "1")
     (set_tile "prt_12_arc_03" "0")
    )
    ((= prt_pt12_arcsld "prt_12_arcsld_03")
     (setq prt_pt12_arc "prt_12_arc_03")
     (set_tile "prt_12_arc_01" "0")
     (set_tile "prt_12_arc_02" "0")
     (set_tile "prt_12_arc_03" "1")
    )
  )
)


;Espessura por Pick Points
(defun prt_12_poe_button_act ()
  (prt_pt12_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt12_poe (rtos new_dist 2 2))
      (prt_pt12_writefile)
    )
  )
  (prt_cfg_12)
)


;verifica se o valor de espessura entrado é válido
(defun prt_12_poe_edit_act ()
  (setq prt_var_newpoe $value)
  (if (distof prt_var_newpoe)
    (progn
      (setq prt_pt12_poe prt_var_newpoe)
      (prt_pt12_writefile)
    )
    (progn
      (alert "Valor Inválido!")
      (set_tile "prt_12_poe_edit" prt_pt12_poe)
      (mode_tile "prt_12_poe_edit" 2)
    )
  )
)  

;lê os dados iniciais da DCL no arquivo de dados
(defun prt_pt12_file ()
  (if (findfile (strcat cnp_root "/config/prt_pt12.txt"))
    (prt_pt12_readfile)
    (progn
      (setq file (open (strcat cnp_root "/config/prt_pt12.txt") "w" "utf8"))
      (write-line "3" file)
      (write-line "1" file)
      (write-line "1" file)      
      (write-line "1" file)
      (write-line "1" file)
      (write-line "prt_12_arc_01" file)
      (write-line "prt_12_cxi_01" file)
      (write-line "prt_12_mac_01" file)
      (close file)
      (prt_pt12_readfile)
    )
  )
)


;função que lê o arquivo de dados
(defun prt_pt12_readfile ()
  (setq	file (open (strcat cnp_root "/config/prt_pt12.txt") "r" "utf8"))
  (setq	prt_pt12_poe (read-line file))
  (setq	prt_pt12_soi (read-line file))
  (setq	prt_pt12_soe (read-line file))
  (setq	prt_pt12_ali (read-line file))
  (setq	prt_pt12_ale (read-line file))
  (setq	prt_pt12_arc (read-line file))
  (setq	prt_pt12_cxi (read-line file))
  (setq	prt_pt12_mac (read-line file))
  (close file)
)

;função que escreve o arquivo de dados
(defun prt_pt12_writefile ()
  (setq	file (open (strcat cnp_root "/config/prt_pt12.txt") "w" "utf8"))
  (write-line prt_pt12_poe file)
  (write-line prt_pt12_soi file)
  (write-line prt_pt12_soe file)
  (write-line prt_pt12_ali file)
  (write-line prt_pt12_ale file)
  (write-line prt_pt12_arc file)
  (write-line prt_pt12_cxi file)
  (write-line prt_pt12_mac file)
  (close file)
)

;Desenha a porta
(defun prt_drw12 ()
  (cn7_init)
  (guarda '("blipmode" "cecolor" "celtype" "clayer" "cmdecho" "orthomode"
          "textstyle" "luprec" "osmode" ))
  (setvar "cecolor" "bylayer")
  (prt_pt12_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 2.0)
  (prt_drw12_caixilho)
  (prt_drw12_porta)
  (prt_drw12_arco)
  (if (/= prt_pt12_mac "prt_12_mac_05")
    (prt_drw12_maçaneta)
  )
  (prt_drw12_soleira)
  (if (/= 0.0 prt_caix)
    (prt_drw12_alisar)
  )
  (devolve)
  (prompt "\nUse o comando <UB> para retornar... ")
)


;*****************************************
;Desenho das Alisares                     
;*****************************************
(defun prt_drw12_alisar ()
  (cn7_verylayer prt_layc_all 7)
  (setvar "cecolor" prt_layc_alc)
  ;internos
  (if (= "1" prt_pt12_ali)
    (progn
      (if (= prt_pt12_cxi "prt_12_cxi_01")
	(setq prt_ali_b1 (polar prt_cxi2 prt_angbase (* 1.0 prt_fator)))
	(setq prt_ali_b1 (polar prt_cxi5 prt_angbase (* 1.0 prt_fator)))
      )
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt12_ale)
    (progn
      (if (= prt_pt12_cxi "prt_12_cxi_01")
	(progn
	  (setq prt_ale_a1 (polar prt_cxi3 (+ prt_angbase pi) (* 1.0 prt_fator)))
	  (setq prt_ale_b1 (polar prt_cxi4 prt_angbase (* 1.0 prt_fator)))
	)
	(progn
	  (setq prt_ale_a1 (polar prt_cxi4 (+ prt_angbase pi) (* 1.0 prt_fator)))
	  (setq prt_ale_b1 (polar prt_cxi8 prt_angbase (* 1.0 prt_fator)))
	)
      )
      (setq prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw12_soleira ()
  (cn7_verylayer prt_layc_sol 7)
  (setvar "cecolor" prt_layc_soc)
  (if (/= prt_caix 0.0)
    (progn
      (if (= prt_pt12_soi "1")
	(if (= prt_pt12_cxi "prt_12_cxi_01")
	  (command "._line" "_non" prt_porta2 "_non" prt_cxi2 "")
	  (command "._line" "_non" prt_porta2 "_non" prt_cxi5 "")
	  )
      )
      (if (= prt_pt12_soe "1")
	(if (= prt_pt12_cxi "prt_12_cxi_01")
	  (command "._line" "_non" prt_cxi3 "_non" prt_cxi4 "")
	  (command "._line" "_non" prt_cxi4 "_non" prt_cxi8 "")
        )
      )
    )
    (progn
      (if (= prt_pt12_soi "1") (command "._line" "_non" prt_brk1 "_non" prt_brk2 ""))
      (if (= prt_pt12_soe "1") (command "._line" "_non" prt_brk3 "_non" prt_brk4 ""))
    )
  )
)

;*****************************************
;Desenho das Maçanetas                    
;*****************************************
(defun prt_drw12_maçaneta ()
  (setq prt_mac1 (polar prt_porta4 prt_angortho (* 7.0 prt_fator))
	prt_mac2 (polar prt_porta3 prt_angortho (* 7.0 prt_fator))
  )
  (cond
    ((= prt_pt12_mac "prt_12_mac_01") (setq prt_mac_blk "prt_mac01"))
    ((= prt_pt12_mac "prt_12_mac_02") (setq prt_mac_blk "prt_mac02"))
    ((= prt_pt12_mac "prt_12_mac_03") (setq prt_mac_blk "prt_mac03"))
    ((= prt_pt12_mac "prt_12_mac_04") (setq prt_mac_blk "prt_mac04"))
  )
  (cn7_verylayer prt_layc_mal 7)
  (if (= prt_code 1)
    (cond
      ((or (= prt_xcode 1) (= prt_xcode 3) (= prt_xcode 4))
       (command "._insert" (strcat cnp_root "/blocos/" prt_mac_blk "a.dwg") "_non" prt_mac1 prt_blkscl prt_blkscl "_non" prt_porta4
		"._explode" (entlast) "._chprop" "_p" "" "_p" "_c" prt_layc_mac "_la" prt_layc_mal "")
       (command "._insert" (strcat cnp_root "/blocos/" prt_mac_blk "b.dwg") "_non" prt_mac2 prt_blkscl prt_blkscl "_non" prt_porta3
		"._explode" (entlast) "._chprop" "_p" "" "_p" "_c" prt_layc_mac "_la" prt_layc_mal "")
      )
      ((= prt_xcode 2)
       (command "._insert" (strcat cnp_root "/blocos/" prt_mac_blk "a.dwg") "_non" prt_mac1 prt_blkscl (- prt_blkscl) "_non" prt_porta4
		"._explode" (entlast) "._chprop" "_p" "" "_p" "_c" prt_layc_mac "_la" prt_layc_mal "")
       (command "._insert" (strcat cnp_root "/blocos/" prt_mac_blk "b.dwg") "_non" prt_mac2 prt_blkscl (- prt_blkscl) "_non" prt_porta3
		"._explode" (entlast) "._chprop" "_p" "" "_p" "_c" prt_layc_mac "_la" prt_layc_mal "")
      )
    )
    (cond
      ((or (= prt_xcode 1) (= prt_xcode 4))
       (command "._insert" (strcat cnp_root "/blocos/" prt_mac_blk "a.dwg") "_non" prt_mac1 prt_blkscl (- prt_blkscl) "_non" prt_porta4
		"._explode" (entlast) "._chprop" "_p" "" "_p" "_c" prt_layc_mac "_la" prt_layc_mal "")
       (command "._insert" (strcat cnp_root "/blocos/" prt_mac_blk "b.dwg") "_non" prt_mac2 prt_blkscl (- prt_blkscl) "_non" prt_porta3
		"._explode" (entlast) "._chprop" "_p" "" "_p" "_c" prt_layc_mac "_la" prt_layc_mal "")
      )
      ((or (= prt_xcode 2) (= prt_xcode 3))
       (command "._insert" (strcat cnp_root "/blocos/" prt_mac_blk "a.dwg") "_non" prt_mac1 prt_blkscl prt_blkscl "_non" prt_porta4
		"._explode" (entlast) "._chprop" "_p" "" "_p" "_c" prt_layc_mac "_la" prt_layc_mal "")
       (command "._insert" (strcat cnp_root "/blocos/" prt_mac_blk "b.dwg") "_non" prt_mac2 prt_blkscl prt_blkscl "_non" prt_porta3
		"._explode" (entlast) "._chprop" "_p" "" "_p" "_c" prt_layc_mac "_la" prt_layc_mal "")
      )
    )
  )
)

;*****************************************
;Desenho de Arcos                         
;*****************************************
(defun prt_drw12_arco ()
  (cn7_verylayer prt_layc_arl 7)
  (setvar "cecolor" prt_layc_arc)
  (setq prt_arcstart prt_mid1)
  (cond
    ((= prt_pt12_arc "prt_12_arc_01")
     (setq prt_arctang (polar prt_arcstart (+ prt_angortho pi) prt_larg))
     (command "._arc" "_non" prt_arcstart "_e" "_non" prt_porta3 "_d" "_non" prt_arctang
	      "._mirror" (entlast) "" "_non" prt_mid1 "_non" prt_mid2 "")
    )
    ((= prt_pt12_arc "prt_12_arc_02")
     (command "._line" "_non" prt_arcstart "_non" prt_porta3 ""
	      "._mirror" (entlast) "" "_non" prt_mid1 "_non" prt_mid2 "")
    )
   )
)


;*****************************************
;Desenho de Portas                        
;*****************************************
(defun prt_drw12_porta ()
  (setq prt_porta2 (polar prt_porta1 prt_angbase (* prt_fator (distof prt_pt12_poe)))
	prt_porta3 (polar prt_porta2 (+ prt_angortho pi) (/ prt_larg 2.0))
	prt_porta4 (polar prt_porta1 (+ prt_angortho pi) (/ prt_larg 2.0))
  )
  (cn7_verylayer prt_layc_pol 7)
  (setvar "cecolor" prt_layc_poc)
  (command "._pline"  "_non" prt_porta1 "_non" prt_porta2  "_non" prt_porta3 "_non" prt_porta4 "_c")
  (command "._mirror" (entlast) "" "_non" prt_mid1 "_non" prt_mid2 "")
)


;*****************************************
;Desenho de Caixilho                      
;*****************************************

;desenha os caixihos
(defun prt_drw12_caixilho ()
  (setq prt_mid1 (polar prt_brk1 prt_angbase (/ (distance prt_brk1 prt_brk2) 2.0))
	prt_mid2 (polar prt_brk3 prt_angbase (/ (distance prt_brk3 prt_brk4) 2.0))
  )
  (cn7_verylayer prt_layc_cxl 7)
  (setvar "cecolor" prt_layc_cxc)
  (if (/= 0.0 prt_caix)
    (progn
      (if (= prt_pt12_cxi "prt_12_cxi_01")
	(progn
	  (setq prt_cxi1 (polar prt_brk1 prt_angbase prt_caix)
		prt_cxi2 (polar prt_cxi1 prt_angbase prt_larg)
		prt_cxi3 (polar prt_brk3 prt_angbase prt_caix)
		prt_cxi4 (polar prt_cxi3 prt_angbase prt_larg)
		)
	  (command "._pline"  "_non" prt_brk1 "_non" prt_cxi1  "_non" prt_cxi3 "_non" prt_brk3 "" ;"_c"
		   "._pline"  "_non" prt_brk2 "_non" prt_cxi2  "_non" prt_cxi4 "_non" prt_brk4 "" ;"_c"
          )
	  (setq prt_arcstart prt_cxi2)
	)
	(progn
	  (setq prt_cxi1 (polar prt_brk1 prt_angbase prt_caix)
		prt_cxi2 (polar prt_cxi1 prt_angortho (* prt_fator (distof prt_pt12_poe)) )
		prt_cxi3 (polar prt_cxi2 prt_angbase (* prt_fator 2.0))
		prt_cxi4 (polar prt_brk3 prt_angbase (+ prt_caix (* prt_fator 2.0)))
		)
	  (command "._pline"  "_non" prt_brk1 "_non" prt_cxi1  "_non" prt_cxi2 "_non" prt_cxi3 "_non" prt_cxi4 "_non" prt_brk3 "");"_c")
	  (setq prt_cxi5 (polar prt_cxi1 prt_angbase prt_larg)
		prt_cxi6 (polar prt_cxi5 prt_angortho (* prt_fator (distof prt_pt12_poe)))
		prt_cxi7 (polar prt_cxi6 (+ pi prt_angbase) (* prt_fator 2.0))
		prt_cxi8 (polar prt_brk4 (+ pi prt_angbase) (+ prt_caix (* prt_fator 2.0)))
		)
	  (command "._pline"  "_non" prt_brk2 "_non" prt_cxi5  "_non" prt_cxi6 "_non" prt_cxi7 "_non" prt_cxi8 "_non" prt_brk4 "");"_c")
	  (setq prt_arcstart prt_cxi5)
        )
      )
      (setq prt_porta1 prt_cxi1)
    )
    ;se o caixilho for nulo
    (progn
      (setq prt_cxi1 prt_brk1
	    prt_cxi2 prt_brk2
	    prt_cxi3 prt_brk3
            prt_cxi4 prt_brk4
	    prt_arcstart prt_cxi2
	    prt_porta1 prt_cxi1
      )
    )
  )
)



;***********************************
;Porta Tipo 13                      
;Parte 01 - Configuração            
;***********************************
(defun prt_cfg_13 ()
  (prt_pt13_file)
  (setq dcl_id (load_dialog (strcat cnp_root "/lisp/cadnorma.dcl")))
  (if (not (new_dialog "prt_cfg_p13" dcl_id)) (exit))
  (set_tile "prt_descr" "Vão Livre (sem porta)")
  ;slide de tipo
  (setq x (dimx_tile "prt_13_slide")
	y (dimy_tile "prt_13_slide")
  )
  (start_image "prt_13_slide")
  (fill_image 0 0 x y -2)
  (slide_image 0 0 x y (strcat cnp_root "/slides/prt_" prt_var_tipo ".sld"))
  (end_image)
  ;soleira
  (if (= "1" prt_pt13_soi) (set_tile "prt_13_solint"  "1"))
  (action_tile "prt_13_solint"  "(setq prt_pt13_soi $value)")
  (if (= "1" prt_pt13_soe) (set_tile "prt_13_solext"  "1"))
  (action_tile "prt_13_solext"  "(setq prt_pt13_soe $value)")
  ;alisares
  (if (= "1" prt_pt13_ali) (set_tile "prt_13_aliint"  "1"))
  (action_tile "prt_13_aliint"  "(setq prt_pt13_ali $value)")
  (if (= "1" prt_pt13_ale) (set_tile "prt_13_aliext"  "1"))
  (action_tile "prt_13_aliext"  "(setq prt_pt13_ale $value)")
  ;ok_cancel
  (action_tile "cancel" "(done_dialog 0)")
  (action_tile "accept" "(done_dialog 1)")
  ;start_dialog
  (setq prt_13_id (start_dialog))
  (unload_dialog dcl_id)
  (if (= prt_13_id 1) (prt_pt13_writefile))
  (if (= prt_13_id 2) (prt_13_poe_button_act))
)


;lê os dados iniciais da DCL no arquivo de dados
(defun prt_pt13_file ()
  (if (findfile (strcat cnp_root "/config/prt_pt13.txt"))
    (prt_pt13_readfile)
    (progn
      (setq file (open (strcat cnp_root "/config/prt_pt13.txt") "w" "utf8"))
      (write-line "1" file)
      (write-line "1" file)      
      (write-line "1" file)
      (write-line "1" file)
      (close file)
      (prt_pt13_readfile)
    )
  )
)

;função que lê o arquivo de dados
(defun prt_pt13_readfile ()
  (setq	file (open (strcat cnp_root "/config/prt_pt13.txt") "r" "utf8"))
  (setq	prt_pt13_soi (read-line file))
  (setq	prt_pt13_soe (read-line file))
  (setq	prt_pt13_ali (read-line file))
  (setq	prt_pt13_ale (read-line file))
  (close file)
)

;função que escreve o arquivo de dados
(defun prt_pt13_writefile ()
  (setq	file (open (strcat cnp_root "/config/prt_pt13.txt") "w" "utf8"))
  (write-line prt_pt13_soi file)
  (write-line prt_pt13_soe file)
  (write-line prt_pt13_ali file)
  (write-line prt_pt13_ale file)
  (close file)
)

;Desenha a porta
(defun prt_drw13 ()
  (cn7_init)
  (guarda '("blipmode" "cecolor" "celtype" "clayer" "cmdecho" "orthomode"
          "textstyle" "luprec" "osmode" ))
  (setvar "cecolor" "bylayer")
  (prt_pt13_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 1.0)
  (prt_drw13_caixilho)
  (prt_drw13_soleira)
  (if (/= 0.0 prt_caix)
    (prt_drw13_alisar)
  )
  (devolve)
  (prompt "\nUse o comando <UB> para retornar... ")
)


;*****************************************
;Desenho das Alisares                     
;*****************************************
(defun prt_drw13_alisar ()
  (cn7_verylayer prt_layc_all 7)
  (setvar "cecolor" prt_layc_alc)
  ;internos
  (if (= "1" prt_pt13_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt13_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw13_soleira ()
  (cn7_verylayer prt_layc_sol 7)
  (setvar "cecolor" prt_layc_soc)
  (if (= prt_pt13_soi "1")
    (command "._line" "_non" prt_cxi1 "_non" prt_cxi2 "")
  )
  (if (= prt_pt13_soe "1")
    (command "._line" "_non" prt_cxi3 "_non" prt_cxi4 "")
  )
)

;*****************************************
;Desenho de Caixilho                      
;*****************************************

;desenha os caixihos
(defun prt_drw13_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 14                      
;Parte 01 - Configuração            
;***********************************
(defun prt_cfg_14 ()
  (prt_pt14_file)
  (setq dcl_id (load_dialog (strcat cnp_root "/lisp/cadnorma.dcl")))
  (if (not (new_dialog "prt_cfg_p14" dcl_id)) (exit))
  (set_tile "prt_descr" "Porta Simples Fechada ('de Abrir')")
  ;slide de tipo
  (setq x (dimx_tile "prt_14_slide")
	y (dimy_tile "prt_14_slide")
  )
  (start_image "prt_14_slide")
  (fill_image 0 0 x y -2)
  (slide_image 0 0 x y (strcat cnp_root "/slides/prt_" prt_var_tipo ".sld"))
  (end_image)
  ;espessura da porta
  (set_tile "prt_14_poe_edit" prt_pt14_poe)
  (action_tile "prt_14_poe_edit" "(prt_14_poe_edit_act)")
  (action_tile "prt_14_poe_pick" "(done_dialog 2)")
  ;soleira
  (if (= "1" prt_pt14_soe) (set_tile "prt_14_solext"  "1"))
  (action_tile "prt_14_solext"  "(setq prt_pt14_soe $value)")
  ;alisares
  (if (= "1" prt_pt14_ali) (set_tile "prt_14_aliint"  "1"))
  (action_tile "prt_14_aliint"  "(setq prt_pt14_ali $value)")
  (if (= "1" prt_pt14_ale) (set_tile "prt_14_aliext"  "1"))
  (action_tile "prt_14_aliext"  "(setq prt_pt14_ale $value)")
  ;tipo de caixilho
  (setq x (dimx_tile "prt_14_cxisld_01")
	y (dimy_tile "prt_14_cxisld_01")
  )
  (start_image "prt_14_cxisld_01")
  (fill_image 0 0 x y -2)
  (slide_image 0 0 x y (strcat cnp_root "/slides/prt_cxi_01.sld"))
  (end_image)
  (setq x (dimx_tile "prt_14_cxisld_02")
	y (dimy_tile "prt_14_cxisld_02")
  )
  (start_image "prt_14_cxisld_02")
  (fill_image 0 0 x y -2)
  (slide_image 0 0 x y (strcat cnp_root "/slides/prt_cxi_02.sld"))
  (end_image)
  (action_tile "prt_14_cxisld_01" "(prt_14_cxisld_act)")
  (action_tile "prt_14_cxisld_02" "(prt_14_cxisld_act)")
  (cond
    ((= prt_pt14_cxi "prt_14_cxi_01") (set_tile "prt_14_cxi_01" "1"))
    ((= prt_pt14_cxi "prt_14_cxi_02") (set_tile "prt_14_cxi_02" "1"))
  )
  (action_tile "prt_14_cxi_01" "(prt_14_cxi_act)")
  (action_tile "prt_14_cxi_02" "(prt_14_cxi_act)")
  ;tipo de maçaneta
  (setq x (dimx_tile "prt_14_macsld_01")
	y (dimy_tile "prt_14_macsld_01")
  )
  (start_image "prt_14_macsld_01")
  (fill_image 0 0 x y -2)
  (slide_image 0 0 x y (strcat cnp_root "/slides/prt_mac_01.sld"))
  (end_image)
  (setq x (dimx_tile "prt_14_macsld_02")
	y (dimy_tile "prt_14_macsld_02")
  )
  (start_image "prt_14_macsld_02")
  (fill_image 0 0 x y -2)
  (slide_image 0 0 x y (strcat cnp_root "/slides/prt_mac_02.sld"))
  (end_image)
  (setq x (dimx_tile "prt_14_macsld_03")
	y (dimy_tile "prt_14_macsld_03")
  )
  (start_image "prt_14_macsld_03")
  (fill_image 0 0 x y -2)
  (slide_image 0 0 x y (strcat cnp_root "/slides/prt_mac_03.sld"))
  (end_image)
  (setq x (dimx_tile "prt_14_macsld_04")
	y (dimy_tile "prt_14_macsld_04")
  )
  (start_image "prt_14_macsld_04")
  (fill_image 0 0 x y -2)
  (slide_image 0 0 x y (strcat cnp_root "/slides/prt_mac_04.sld"))
  (end_image)
  (setq x (dimx_tile "prt_14_macsld_05")
	y (dimy_tile "prt_14_macsld_05")
  )
  (start_image "prt_14_macsld_05")
  (fill_image 0 0 x y -2)
  (slide_image 0 0 x y (strcat cnp_root "/slides/prt_mac_05.sld"))
  (end_image)
  (action_tile "prt_14_macsld_01" "(prt_14_macsld_act)")
  (action_tile "prt_14_macsld_02" "(prt_14_macsld_act)")
  (action_tile "prt_14_macsld_03" "(prt_14_macsld_act)")
  (action_tile "prt_14_macsld_04" "(prt_14_macsld_act)")
  (action_tile "prt_14_macsld_05" "(prt_14_macsld_act)")
  (cond
    ((= prt_pt14_mac "prt_14_mac_01") (set_tile "prt_14_mac_01" "1"))
    ((= prt_pt14_mac "prt_14_mac_02") (set_tile "prt_14_mac_02" "1"))
    ((= prt_pt14_mac "prt_14_mac_03") (set_tile "prt_14_mac_03" "1"))
    ((= prt_pt14_mac "prt_14_mac_04") (set_tile "prt_14_mac_04" "1"))
    ((= prt_pt14_mac "prt_14_mac_05") (set_tile "prt_14_mac_05" "1"))
  )
  (action_tile "prt_14_mac_01" "(prt_14_mac_act)")
  (action_tile "prt_14_mac_02" "(prt_14_mac_act)")
  (action_tile "prt_14_mac_03" "(prt_14_mac_act)")
  (action_tile "prt_14_mac_04" "(prt_14_mac_act)")
  (action_tile "prt_14_mac_05" "(prt_14_mac_act)")
  ;ok_cancel
  (action_tile "cancel" "(done_dialog 0)")
  (action_tile "accept" "(done_dialog 1)")
  ;start_dialog
  (setq prt_14_id (start_dialog))
  (unload_dialog dcl_id)
  (if (= prt_14_id 1) (prt_pt14_writefile))
  (if (= prt_14_id 2) (prt_14_poe_button_act))
)

;radio_buttons para maçanetas
(defun prt_14_mac_act ()
  (setq prt_pt14_mac $key)
  (cond
    ((= prt_pt14_mac "prt_14_mac_01")
     (set_tile "prt_14_mac_01" "1")
     (set_tile "prt_14_mac_02" "0")
     (set_tile "prt_14_mac_03" "0")
     (set_tile "prt_14_mac_04" "0")
     (set_tile "prt_14_mac_05" "0")
    )
    ((= prt_pt14_mac "prt_14_mac_01")
     (set_tile "prt_14_mac_01" "0")
     (set_tile "prt_14_mac_02" "1")
     (set_tile "prt_14_mac_03" "0")
     (set_tile "prt_14_mac_04" "0")
     (set_tile "prt_14_mac_05" "0")
    )
    ((= prt_pt14_mac "prt_14_mac_01")
     (set_tile "prt_14_mac_01" "0")
     (set_tile "prt_14_mac_02" "0")
     (set_tile "prt_14_mac_03" "1")
     (set_tile "prt_14_mac_04" "0")
     (set_tile "prt_14_mac_05" "0")
    )
    ((= prt_pt14_mac "prt_14_mac_01")
     (set_tile "prt_14_mac_01" "0")
     (set_tile "prt_14_mac_02" "0")
     (set_tile "prt_14_mac_03" "0")
     (set_tile "prt_14_mac_04" "1")
     (set_tile "prt_14_mac_05" "0")
    )
    ((= prt_pt14_mac "prt_14_mac_01")
     (set_tile "prt_14_mac_01" "0")
     (set_tile "prt_14_mac_02" "0")
     (set_tile "prt_14_mac_03" "0")
     (set_tile "prt_14_mac_04" "0")
     (set_tile "prt_14_mac_05" "1")
    )
  )
)

;slides de tipo de maçaneta
(defun prt_14_macsld_act ()
  (setq prt_pt14_macsld $key)
  (cond
    ((= prt_pt14_macsld "prt_14_macsld_01")
     (setq prt_pt14_mac "prt_14_mac_01")
     (set_tile "prt_14_mac_01" "1")
     (set_tile "prt_14_mac_02" "0")
     (set_tile "prt_14_mac_03" "0")
     (set_tile "prt_14_mac_04" "0")
     (set_tile "prt_14_mac_05" "0")
    )
    ((= prt_pt14_macsld "prt_14_macsld_02")
     (setq prt_pt14_mac "prt_14_mac_02")
     (set_tile "prt_14_mac_01" "0")
     (set_tile "prt_14_mac_02" "1")
     (set_tile "prt_14_mac_03" "0")
     (set_tile "prt_14_mac_04" "0")
     (set_tile "prt_14_mac_05" "0")
    )
    ((= prt_pt14_macsld "prt_14_macsld_03")
     (setq prt_pt14_mac "prt_14_mac_03")
     (set_tile "prt_14_mac_01" "0")
     (set_tile "prt_14_mac_02" "0")
     (set_tile "prt_14_mac_03" "1")
     (set_tile "prt_14_mac_04" "0")
     (set_tile "prt_14_mac_05" "0")
    )
    ((= prt_pt14_macsld "prt_14_macsld_04")
     (setq prt_pt14_mac "prt_14_mac_04")
     (set_tile "prt_14_mac_01" "0")
     (set_tile "prt_14_mac_02" "0")
     (set_tile "prt_14_mac_03" "0")
     (set_tile "prt_14_mac_04" "1")
     (set_tile "prt_14_mac_05" "0")
    )
    ((= prt_pt14_macsld "prt_14_macsld_05")
     (setq prt_pt14_mac "prt_14_mac_05")
     (set_tile "prt_14_mac_01" "0")
     (set_tile "prt_14_mac_02" "0")
     (set_tile "prt_14_mac_03" "0")
     (set_tile "prt_14_mac_04" "0")
     (set_tile "prt_14_mac_05" "1")
    )
  )
)


;radio_buttons para caixilho
(defun prt_14_cxi_act ()
  (setq prt_pt14_cxi $key)
  (cond
    ((= prt_pt14_cxi "prt_14_cxi_01")
     (set_tile "prt_14_cxi_01" "1")
     (set_tile "prt_14_cxi_02" "0")
    )
    ((= prt_pt14_cxi "prt_14_cxi_02")
     (set_tile "prt_14_cxi_01" "0")
     (set_tile "prt_14_cxi_02" "1")
    )
  )
)

;slides de tipo de caixilho
(defun prt_14_cxisld_act ()
  (setq prt_pt14_cxisld $key)
  (cond
    ((= prt_pt14_cxisld "prt_14_cxisld_01")
     (setq prt_pt14_cxi "prt_14_cxi_01")
     (set_tile "prt_14_cxi_01" "1")
     (set_tile "prt_14_cxi_02" "0")
     (set_tile "prt_14_cxi_03" "0")
    )
    ((= prt_pt14_cxisld "prt_14_cxisld_02")
     (setq prt_pt14_cxi "prt_14_cxi_02")
     (set_tile "prt_14_cxi_01" "0")
     (set_tile "prt_14_cxi_02" "1")
     (set_tile "prt_14_cxi_03" "0")
    )
    ((= prt_pt14_cxisld "prt_14_cxisld_03")
     (setq prt_pt14_cxi "prt_14_cxi_03")
     (set_tile "prt_14_cxi_01" "0")
     (set_tile "prt_14_cxi_02" "0")
     (set_tile "prt_14_cxi_03" "1")
    )
  )
)

;Espessura por Pick Points
(defun prt_14_poe_button_act ()
  (prt_pt14_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt14_poe (rtos new_dist 2 2))
      (prt_pt14_writefile)
    )
  )
  (prt_cfg_14)
)


;verifica se o valor de espessura entrado é válido
(defun prt_14_poe_edit_act ()
  (setq prt_var_newpoe $value)
  (if (distof prt_var_newpoe)
    (progn
      (setq prt_pt14_poe prt_var_newpoe)
      (prt_pt14_writefile)
    )
    (progn
      (alert "Valor Inválido!")
      (set_tile "prt_14_poe_edit" prt_pt14_poe)
      (mode_tile "prt_14_poe_edit" 2)
    )
  )
)  

;lê os dados iniciais da DCL no arquivo de dados
(defun prt_pt14_file ()
  (if (findfile (strcat cnp_root "/config/prt_pt14.txt"))
    (prt_pt14_readfile)
    (progn
      (setq file (open (strcat cnp_root "/config/prt_pt14.txt") "w" "utf8"))
      (write-line "3" file)
      (write-line "1" file)
      (write-line "1" file)      
      (write-line "1" file)
      (write-line "1" file)
      (write-line "prt_14_arc_01" file)
      (write-line "prt_14_cxi_01" file)
      (write-line "prt_14_mac_01" file)
      (close file)
      (prt_pt14_readfile)
    )
  )
)


;função que lê o arquivo de dados
(defun prt_pt14_readfile ()
  (setq	file (open (strcat cnp_root "/config/prt_pt14.txt") "r" "utf8"))
  (setq	prt_pt14_poe (read-line file))
  (setq	prt_pt14_soi (read-line file))
  (setq	prt_pt14_soe (read-line file))
  (setq	prt_pt14_ali (read-line file))
  (setq	prt_pt14_ale (read-line file))
  (setq	prt_pt14_arc (read-line file))
  (setq	prt_pt14_cxi (read-line file))
  (setq	prt_pt14_mac (read-line file))
  (close file)
)

;função que escreve o arquivo de dados
(defun prt_pt14_writefile ()
  (setq	file (open (strcat cnp_root "/config/prt_pt14.txt") "w" "utf8"))
  (write-line prt_pt14_poe file)
  (write-line prt_pt14_soi file)
  (write-line prt_pt14_soe file)
  (write-line prt_pt14_ali file)
  (write-line prt_pt14_ale file)
  (write-line prt_pt14_arc file)
  (write-line prt_pt14_cxi file)
  (write-line prt_pt14_mac file)
  (close file)
)

;Desenha a porta
(defun prt_drw14 ()
  (cn7_init)
  (guarda '("blipmode" "cecolor" "celtype" "clayer" "cmdecho" "orthomode"
          "textstyle" "luprec" "osmode" ))
  (setvar "cecolor" "bylayer")
  (prt_pt14_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 1.0)
  (prt_drw14_caixilho)
  (prt_drw14_porta)
  (prt_drw14_maçaneta)
  (prt_drw14_soleira)
  (if (/= 0.0 prt_caix)
    (prt_drw14_alisar)
  )
  (devolve)
  (prompt "\nUse o comando <UB> para retornar... ")
)


;*****************************************
;Desenho das Alisares                     
;*****************************************
(defun prt_drw14_alisar ()
  (cn7_verylayer prt_layc_all 7)
  (setvar "cecolor" prt_layc_alc)
  ;internos
  (if (= "1" prt_pt14_ali)
    (progn
      (if (= prt_pt14_cxi "prt_14_cxi_01")
	(setq prt_ali_b1 (polar prt_cxi2 prt_angbase (* 1.0 prt_fator)))
	(setq prt_ali_b1 (polar prt_cxi5 prt_angbase (* 1.0 prt_fator)))
      )
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt14_ale)
    (progn
      (if (= prt_pt14_cxi "prt_14_cxi_01")
	(progn
	  (setq prt_ale_a1 (polar prt_cxi3 (+ prt_angbase pi) (* 1.0 prt_fator)))
	  (setq prt_ale_b1 (polar prt_cxi4 prt_angbase (* 1.0 prt_fator)))
	)
	(progn
	  (setq prt_ale_a1 (polar prt_cxi4 (+ prt_angbase pi) (* 1.0 prt_fator)))
	  (setq prt_ale_b1 (polar prt_cxi8 prt_angbase (* 1.0 prt_fator)))
	)
      )
      (setq prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw14_soleira ()
  (cn7_verylayer prt_layc_sol 7)
  (setvar "cecolor" prt_layc_soc)
  (if (= prt_pt14_soe "1")
    (if (= prt_pt14_cxi "prt_14_cxi_01")
      (command "._line" "_non" prt_cxi3 "_non" prt_cxi4 "")
      (command "._line" "_non" prt_cxi4 "_non" prt_cxi8 "")
    )
  )
)


;*****************************************
;Desenho das Maçanetas                    
;*****************************************
(defun prt_drw14_maçaneta ()
  (setq prt_mac1 (polar prt_porta4 (+ prt_angbase pi) (* 7.0 prt_fator))
	prt_mac2 (polar prt_porta3 (+ prt_angbase pi) (* 7.0 prt_fator))
  )
  (cond
    ((= prt_pt14_mac "prt_14_mac_01") (setq prt_mac_blk "prt_mac01"))
    ((= prt_pt14_mac "prt_14_mac_02") (setq prt_mac_blk "prt_mac02"))
    ((= prt_pt14_mac "prt_14_mac_03") (setq prt_mac_blk "prt_mac03"))
    ((= prt_pt14_mac "prt_14_mac_04") (setq prt_mac_blk "prt_mac04"))
  )
  (cn7_verylayer prt_layc_mal 7)
  (if (= prt_code 1)
    (cond
      ((or (= prt_xcode 1) (= prt_xcode 3) (= prt_xcode 4))
       (command "._insert" (strcat cnp_root "/blocos/" prt_mac_blk "a.dwg") "_non" prt_mac1 prt_blkscl prt_blkscl "_non" prt_porta4
		"._explode" (entlast) "" "._chprop" "_p" "" "_p" "_c" prt_layc_mac "_la" prt_layc_mal "")
       (command "._insert" (strcat cnp_root "/blocos/" prt_mac_blk "b.dwg") "_non" prt_mac2 prt_blkscl prt_blkscl "_non" prt_porta3
		"._explode" (entlast) "" "._chprop" "_p" "" "_p" "_c" prt_layc_mac "_la" prt_layc_mal "")
      )
      ((= prt_xcode 2)
       (command "._insert" (strcat cnp_root "/blocos/" prt_mac_blk "a.dwg") "_non" prt_mac1 prt_blkscl (- prt_blkscl) "_non" prt_porta4
		"._explode" (entlast) "" "._chprop" "_p" "" "_p" "_c" prt_layc_mac "_la" prt_layc_mal "")
       (command "._insert" (strcat cnp_root "/blocos/" prt_mac_blk "b.dwg") "_non" prt_mac2 prt_blkscl (- prt_blkscl) "_non" prt_porta3
		"._explode" (entlast) "" "._chprop" "_p" "" "_p" "_c" prt_layc_mac "_la" prt_layc_mal "")
      )
    )
    (cond
      ((or (= prt_xcode 1) (= prt_xcode 4))
       (command "._insert" (strcat cnp_root "/blocos/" prt_mac_blk "a.dwg") "_non" prt_mac1 prt_blkscl (- prt_blkscl) "_non" prt_porta4
		"._explode" (entlast) "" "._chprop" "_p" "" "_p" "_c" prt_layc_mac "_la" prt_layc_mal "")
       (command "._insert" (strcat cnp_root "/blocos/" prt_mac_blk "b.dwg") "_non" prt_mac2 prt_blkscl (- prt_blkscl) "_non" prt_porta3
		"._explode" (entlast) "" "._chprop" "_p" "" "_p" "_c" prt_layc_mac "_la" prt_layc_mal "")
      )
      ((or (= prt_xcode 2) (= prt_xcode 3))
       (command "._insert" (strcat cnp_root "/blocos/" prt_mac_blk "a.dwg") "_non" prt_mac1 prt_blkscl prt_blkscl "_non" prt_porta4
		"._explode" (entlast) "" "._chprop" "_p" "" "_p" "_c" prt_layc_mac "_la" prt_layc_mal "")
       (command "._insert" (strcat cnp_root "/blocos/" prt_mac_blk "b.dwg") "_non" prt_mac2 prt_blkscl prt_blkscl "_non" prt_porta3
		"._explode" (entlast) "" "._chprop" "_p" "" "_p" "_c" prt_layc_mac "_la" prt_layc_mal "")
      )
    )
  )
)

;*****************************************
;Desenho de Portas                        
;*****************************************
(defun prt_drw14_porta ()
  (setq prt_porta2 (polar prt_porta1 prt_angortho (* prt_fator (distof prt_pt14_poe)))
	prt_porta3 (polar prt_porta2 prt_angbase prt_larg)
	prt_porta4 (polar prt_porta1 prt_angbase prt_larg)
  )
  (cn7_verylayer prt_layc_pol 7)
  (setvar "cecolor" prt_layc_poc)
  (command "._pline"  "_non" prt_porta1 "_non" prt_porta2  "_non" prt_porta3 "_non" prt_porta4 "_c")
)


;*****************************************
;Desenho de Caixilho                      
;*****************************************

;desenha os caixihos
(defun prt_drw14_caixilho ()
  (cn7_verylayer prt_layc_cxl 7)
  (setvar "cecolor" prt_layc_cxc)
  (if (/= 0.0 prt_caix)
    (progn
      (if (= prt_pt14_cxi "prt_14_cxi_01")
	(progn
	  (setq prt_cxi1 (polar prt_brk1 prt_angbase prt_caix)
		prt_cxi2 (polar prt_cxi1 prt_angbase prt_larg)
		prt_cxi3 (polar prt_brk3 prt_angbase prt_caix)
		prt_cxi4 (polar prt_cxi3 prt_angbase prt_larg)
		)
	  (command "._pline"  "_non" prt_brk1 "_non" prt_cxi1  "_non" prt_cxi3 "_non" prt_brk3 "" ;"_c"
		   "._pline"  "_non" prt_brk2 "_non" prt_cxi2  "_non" prt_cxi4 "_non" prt_brk4 "" ;"_c"
          )
	  (setq prt_arcstart prt_cxi2)
	)
	(progn
	  (setq prt_cxi1 (polar prt_brk1 prt_angbase prt_caix)
		prt_cxi2 (polar prt_cxi1 prt_angortho (* prt_fator (distof prt_pt14_poe)) )
		prt_cxi3 (polar prt_cxi2 prt_angbase (* prt_fator 2.0))
		prt_cxi4 (polar prt_brk3 prt_angbase (+ prt_caix (* prt_fator 2.0)))
		)
	  (command "._pline"  "_non" prt_brk1 "_non" prt_cxi1  "_non" prt_cxi2 "_non" prt_cxi3 "_non" prt_cxi4 "_non" prt_brk3 "");"_c")
	  (setq prt_cxi5 (polar prt_cxi1 prt_angbase prt_larg)
		prt_cxi6 (polar prt_cxi5 prt_angortho (* prt_fator (distof prt_pt14_poe)))
		prt_cxi7 (polar prt_cxi6 (+ pi prt_angbase) (* prt_fator 2.0))
		prt_cxi8 (polar prt_brk4 (+ pi prt_angbase) (+ prt_caix (* prt_fator 2.0)))
		)
	  (command "._pline"  "_non" prt_brk2 "_non" prt_cxi5  "_non" prt_cxi6 "_non" prt_cxi7 "_non" prt_cxi8 "_non" prt_brk4 "");"_c")
	  (setq prt_arcstart prt_cxi5)
        )
      )
      (setq prt_porta1 prt_cxi1)
    )
    ;se o caixilho for nulo
    (progn
      (setq prt_cxi1 prt_brk1
	    prt_cxi2 prt_brk2
	    prt_cxi3 prt_brk3
	    prt_cxi5 prt_brk2
	    prt_cxi8 prt_brk4
	    prt_arcstart prt_cxi2
	    prt_porta1 prt_cxi1
      )
      (if (= prt_pt14_cxi "prt_14_cxi_01")
	(setq prt_cxi4 prt_brk4)
	(setq prt_cxi4 prt_brk3)
      )
    )
  )
)



;***********************************
;Porta Tipo 21                      
;Parte 01 - Configuração            
;***********************************
(defun prt_cfg_21 ()
  (prt_pt21_file)
  (setq dcl_id (load_dialog (strcat cnp_root "/lisp/cadnorma.dcl")))
  (if (not (new_dialog "prt_cfg_p21" dcl_id)) (exit))
  (set_tile "prt_descr" "Porta Deslizante Simples ('de Correr')")
  ;slide de tipo
  (setq x (dimx_tile "prt_21_slide")
	y (dimy_tile "prt_21_slide")
  )
  (start_image "prt_21_slide")
  (fill_image 0 0 x y -2)
  (slide_image 0 0 x y (strcat cnp_root "/slides/prt_" prt_var_tipo ".sld"))
  (end_image)
  ;espessura da porta
  (set_tile "prt_21_poe_edit" prt_pt21_poe)
  (action_tile "prt_21_poe_edit" "(prt_21_poe_edit_act)")
  (action_tile "prt_21_poe_pick" "(done_dialog 2)")
  ;soleira
  (if (= "1" prt_pt21_soi) (set_tile "prt_21_solint"  "1"))
  (action_tile "prt_21_solint"  "(setq prt_pt21_soi $value)")
  (if (= "1" prt_pt21_soe) (set_tile "prt_21_solext"  "1"))
  (action_tile "prt_21_solext"  "(setq prt_pt21_soe $value)")
  ;alisares
  (if (= "1" prt_pt21_ali) (set_tile "prt_21_aliint"  "1"))
  (action_tile "prt_21_aliint"  "(setq prt_pt21_ali $value)")
  (if (= "1" prt_pt21_ale) (set_tile "prt_21_aliext"  "1"))
  (action_tile "prt_21_aliext"  "(setq prt_pt21_ale $value)")
  ;tipo de posicionamento (interna ou externa)
  (setq x (dimx_tile "prt_21_possld_01")
	y (dimy_tile "prt_21_possld_01")
  )
  (start_image "prt_21_possld_01")
  (fill_image 0 0 x y -2)
  (slide_image 0 0 x y (strcat cnp_root "/slides/prt_pos_2101.sld"))
  (end_image)
  (setq x (dimx_tile "prt_21_possld_02")
	y (dimy_tile "prt_21_possld_02")
  )
  (start_image "prt_21_possld_02")
  (fill_image 0 0 x y -2)
  (slide_image 0 0 x y (strcat cnp_root "/slides/prt_pos_2102.sld"))
  (end_image)
  (action_tile "prt_21_possld_01" "(prt_21_possld_act)")
  (action_tile "prt_21_possld_02" "(prt_21_possld_act)")
  (cond
    ((= prt_pt21_pos "prt_21_pos_01") (set_tile "prt_21_pos_01" "1"))
    ((= prt_pt21_pos "prt_21_pos_02") (set_tile "prt_21_pos_02" "1"))
  )
  (action_tile "prt_21_pos_01" "(prt_21_pos_act)")
  (action_tile "prt_21_pos_02" "(prt_21_pos_act)")
  ;tipo de caixilho
  (setq x (dimx_tile "prt_21_cxisld_01")
	y (dimy_tile "prt_21_cxisld_01")
  )
  (start_image "prt_21_cxisld_01")
  (fill_image 0 0 x y -2)
  (slide_image 0 0 x y (strcat cnp_root "/slides/prt_cxi_01.sld"))
  (end_image)
  (setq x (dimx_tile "prt_21_cxisld_02")
	y (dimy_tile "prt_21_cxisld_02")
  )
  (start_image "prt_21_cxisld_02")
  (fill_image 0 0 x y -2)
  (slide_image 0 0 x y (strcat cnp_root "/slides/prt_cxi_02.sld"))
  (end_image)
  (action_tile "prt_21_cxisld_01" "(prt_21_cxisld_act)")
  (action_tile "prt_21_cxisld_02" "(prt_21_cxisld_act)")
  (cond
    ((= prt_pt21_cxi "prt_21_cxi_01") (set_tile "prt_21_cxi_01" "1"))
    ((= prt_pt21_cxi "prt_21_cxi_02") (set_tile "prt_21_cxi_02" "1"))
  )
  (action_tile "prt_21_cxi_01" "(prt_21_cxi_act)")
  (action_tile "prt_21_cxi_02" "(prt_21_cxi_act)")
  ;ok_cancel
  (action_tile "cancel" "(done_dialog 0)")
  (action_tile "accept" "(done_dialog 1)")
  ;start_dialog
  (setq prt_21_id (start_dialog))
  (unload_dialog dcl_id)
  (if (= prt_21_id 1) (prt_pt21_writefile))
  (if (= prt_21_id 2) (prt_21_poe_button_act))
)

;radio_buttons para caixilho
(defun prt_21_cxi_act ()
  (setq prt_pt21_cxi $key)
  (cond
    ((= prt_pt21_cxi "prt_21_cxi_01")
     (setq prt_pt21_cxi "prt_21_cxi_01")
     (set_tile "prt_21_cxi_01" "1")
     (set_tile "prt_21_cxi_02" "0")
    )
    ((= prt_pt21_cxi "prt_21_cxi_02")
     (setq prt_pt21_cxi "prt_21_cxi_02")
     (set_tile "prt_21_cxi_01" "0")
     (set_tile "prt_21_cxi_02" "1")
    )
  )
)


;slides de tipo de caixilho
(defun prt_21_cxisld_act ()
  (setq prt_pt21_cxisld $key)
  (cond
    ((= prt_pt21_cxisld "prt_21_cxisld_01")
     (setq prt_pt21_cxi "prt_21_cxi_01")
     (set_tile "prt_21_cxi_01" "1")
     (set_tile "prt_21_cxi_02" "0")
    )
    ((= prt_pt21_cxisld "prt_21_cxisld_02")
     (setq prt_pt21_cxi "prt_21_cxi_02")
     (set_tile "prt_21_cxi_01" "0")
     (set_tile "prt_21_cxi_02" "1")
    )
  )
)

;radio_buttons para posicionamento
(defun prt_21_pos_act ()
  (setq prt_pt21_pos $key)
  (cond
    ((= prt_pt21_pos "prt_21_pos_01")
     (set_tile "prt_21_pos_01" "1")
     (set_tile "prt_21_pos_02" "0")
    )
    ((= prt_pt21_pos "prt_21_pos_02")
     (set_tile "prt_21_pos_01" "0")
     (set_tile "prt_21_pos_02" "1")
    )
  )
)

;slides de tipo de posicionamento
(defun prt_21_possld_act ()
  (setq prt_pt21_possld $key)
  (cond
    ((= prt_pt21_possld "prt_21_possld_01")
     (setq prt_pt21_pos "prt_21_pos_01")
     (set_tile "prt_21_pos_01" "1")
     (set_tile "prt_21_pos_02" "0")
    )
    ((= prt_pt21_possld "prt_21_possld_02")
     (setq prt_pt21_pos "prt_21_pos_02")
     (set_tile "prt_21_pos_01" "0")
     (set_tile "prt_21_pos_02" "1")
    )
  )
)


;Espessura por Pick Points
(defun prt_21_poe_button_act ()
  (prt_pt21_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt21_poe (rtos new_dist 2 2))
      (prt_pt21_writefile)
    )
  )
  (prt_cfg_21)
)


;verifica se o valor de espessura entrado é válido
(defun prt_21_poe_edit_act ()
  (setq prt_var_newpoe $value)
  (if (distof prt_var_newpoe)
    (progn
      (setq prt_pt21_poe prt_var_newpoe)
      (prt_pt21_writefile)
    )
    (progn
      (alert "Valor Inválido!")
      (set_tile "prt_21_poe_edit" prt_pt21_poe)
      (mode_tile "prt_21_poe_edit" 2)
    )
  )
)  

;lê os dados iniciais da DCL no arquivo de dados
(defun prt_pt21_file ()
  (if (findfile (strcat cnp_root "/config/prt_pt21.txt"))
    (prt_pt21_readfile)
    (progn
      (setq file (open (strcat cnp_root "/config/prt_pt21.txt") "w" "utf8"))
      (write-line "3" file)
      (write-line "1" file)
      (write-line "1" file)      
      (write-line "1" file)
      (write-line "1" file)
      (write-line "prt_21_pos_01" file)
      (write-line "prt_21_cxi_01" file)
      (close file)
      (prt_pt21_readfile)
    )
  )
)


;função que lê o arquivo de dados
(defun prt_pt21_readfile ()
  (setq	file (open (strcat cnp_root "/config/prt_pt21.txt") "r" "utf8"))
  (setq	prt_pt21_poe (read-line file))
  (setq	prt_pt21_soi (read-line file))
  (setq	prt_pt21_soe (read-line file))
  (setq	prt_pt21_ali (read-line file))
  (setq	prt_pt21_ale (read-line file))
  (setq	prt_pt21_pos (read-line file))
  (setq	prt_pt21_cxi (read-line file))
  (close file)
)

;função que escreve o arquivo de dados
(defun prt_pt21_writefile ()
  (setq	file (open (strcat cnp_root "/config/prt_pt21.txt") "w" "utf8"))
  (write-line prt_pt21_poe file)
  (write-line prt_pt21_soi file)
  (write-line prt_pt21_soe file)
  (write-line prt_pt21_ali file)
  (write-line prt_pt21_ale file)
  (write-line prt_pt21_pos file)
  (write-line prt_pt21_cxi file)
  (close file)
)

;Desenha a porta
(defun prt_drw21 ()
  (cn7_init)
  (guarda '("blipmode" "cecolor" "celtype" "clayer" "cmdecho" "orthomode"
          "textstyle" "luprec" "osmode" ))
  (setvar "cecolor" "bylayer")
  (prt_pt21_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_drw21_openfree)
  (if (= prt_pt21_pos "prt_21_pos_01")
    (prt_drw21a_caixilho)
    (prt_drw21b_caixilho)
  )
  (prt_drw21_porta)
  (prt_drw21_soleira)
  (if (/= 0.0 prt_caix)
    (prt_drw21_alisar)
  )
  (prt_drw21_seta)
  (devolve)
  (prompt "\nUse o comando <UB> para retornar... ")
)

;*****************************************
;Desenho das Setas                        
;*****************************************
(defun prt_drw21_seta ()
  (cn7_verylayer "porta_seta" 1)
  (if (= prt_pt21_pos "prt_21_pos_01")
    (setq prt_seta (polar prt_porta2 prt_angbase (/ prt_larg 2.0))
	  prt_seta (polar prt_seta (+ pi prt_angortho) (* prt_fator 5))
    )
    (setq prt_seta (polar prt_porta1a prt_angbase (/ prt_larg 2.0))
	  prt_seta (polar prt_seta (+ pi prt_angortho) (* prt_fator 5))
    )
  )
  (command "._insert" (strcat cnp_root "/blocos/prt_seta") "_s" (/ prt_blkscl 1.25) "_non" prt_seta (* 180 (/ prt_angbase pi)))
)

;*****************************************
;Desenho das Alisares                     
;*****************************************
(defun prt_drw21_alisar ()
  (cn7_verylayer prt_layc_all 7)
  (setvar "cecolor" prt_layc_alc)
  ;alisares internos
  (if (= "1" prt_pt21_ali)
    (progn
      ;porta externa
      (if (= prt_pt21_pos "prt_21_pos_01")
	(progn
	  (setq prt_ali_a1 (polar prt_cxi1 (+ prt_angbase pi) (* 1.0 prt_fator))
		prt_ali_a2 (polar prt_ali_a1 prt_angortho (* (- (distof prt_pt21_poe) 1.0) prt_fator))
		prt_ali_a3 (polar prt_ali_a2 (+ prt_angbase pi) (* prt_fator 4.0))
		prt_ali_a4 (polar prt_brk1 (+ prt_angbase pi) (* prt_fator 5.0))
	  )
	  (command "._line" "_non" prt_cxi1 "_non" prt_ali_a1 "_non" prt_ali_a2 "_non" prt_ali_a3 "_non" prt_ali_a4 "")
	)
	;porta interna
	(progn
	  (if (= prt_pt21_cxi "prt_21_cxi_01")
	    ;caixiho simples
	    (progn
	      (setq prt_ali_a1 (polar prt_cxi1 (+ prt_angbase pi) (* prt_fator 1.0))
		    prt_ali_a2 (polar prt_ali_a1 (+ prt_angortho pi) (* prt_fator 1.0))
		    prt_ali_a3 (polar prt_ali_a2 (+ prt_angbase pi) (* prt_fator 5.0))
		    prt_ali_a4 (polar prt_ali_a3 prt_angortho (* prt_fator 1.0))
	      )
	      (command "._line" "_non" prt_ali_a1 "_non" prt_ali_a2 "_non" prt_ali_a3 "_non" prt_ali_a4 "")
	      (setq prt_ali_b1 (polar prt_cxi3 prt_angbase (* prt_fator 1.0))
		    prt_ali_b2 (polar prt_ali_b1 (+ prt_angortho pi) (* prt_fator 1.0))
		    prt_ali_b3 (polar prt_ali_b2 prt_angbase (* prt_fator 5.0))
		    prt_ali_b4 (polar prt_ali_b3 prt_angortho (* prt_fator 1.0))
	      )
	      (command "._line" "_non" prt_ali_b1 "_non" prt_ali_b2 "_non" prt_ali_b3 "_non" prt_ali_b4 "")
	    )
	    ;caixilho detalhado
	    (progn
	      (setq prt_ali_a1 (polar prt_cxi1 (+ prt_angbase pi) (* prt_fator 1.0))
		    prt_ali_a2 (polar prt_ali_a1 (+ prt_angortho pi) (* prt_fator 1.0))
		    prt_ali_a3 (polar prt_ali_a2 (+ prt_angbase pi) (* prt_fator 5.0))
		    prt_ali_a4 (polar prt_ali_a3 prt_angortho (* prt_fator 1.0))
	      )
	      (command "._line" "_non" prt_ali_a1 "_non" prt_ali_a2 "_non" prt_ali_a3 "_non" prt_ali_a4 "")
	      (setq prt_ali_b1 (polar prt_cxi5 prt_angbase (* prt_fator 1.0))
		    prt_ali_b2 (polar prt_ali_b1 (+ prt_angortho pi) (* prt_fator 1.0))
		    prt_ali_b3 (polar prt_ali_b2 prt_angbase (* prt_fator 5.0))
		    prt_ali_b4 (polar prt_ali_b3 prt_angortho (* prt_fator 1.0))
	      )
	      (command "._line" "_non" prt_ali_b1 "_non" prt_ali_b2 "_non" prt_ali_b3 "_non" prt_ali_b4 "")
	    )
	  )
	)
      )
    )
  )
  ;alisares externos
  (if (= "1" prt_pt21_ale)
    (progn
      ;porta externa
      (if (= prt_pt21_pos "prt_21_pos_01")
	;caixilho simples
	(if (= prt_pt21_cxi "prt_21_cxi_01")
	  (progn
	    (setq prt_ale_c1 (polar prt_cxi3 (+ prt_angbase pi) (* 1.0 prt_fator))
		  prt_ale_c2 (polar prt_ale_c1 prt_angortho (* prt_fator 1.0))
		  prt_ale_c3 (polar prt_ale_c2 (+ prt_angbase pi) (* prt_fator 5.0))
		  prt_ale_c4 (polar prt_ale_c3 (+ prt_angortho pi) (* prt_fator 1.0))
	    )
	    (command "._line" "_non" prt_ale_c1 "_non" prt_ale_c2 "_non" prt_ale_c3 "_non" prt_ale_c4 "")
	    (setq prt_ale_d1 (polar prt_cxi5 prt_angbase (* 1.0 prt_fator))
		  prt_ale_d2 (polar prt_ale_d1 prt_angortho (* prt_fator 1.0))
		  prt_ale_d3 (polar prt_ale_d2 prt_angbase (* prt_fator 5.0))
		  prt_ale_d4 (polar prt_ale_d3 (+ prt_angortho pi) (* prt_fator 1.0))
	    )
	    (command "._line" "_non" prt_ale_d1 "_non" prt_ale_d2 "_non" prt_ale_d3 "_non" prt_ale_d4 "")
	  )
	  ;caixilho detalhado
	  (progn
	    (setq prt_ale_c1 (polar prt_cxi5 (+ prt_angbase pi) (* 1.0 prt_fator))
		  prt_ale_c2 (polar prt_ale_c1 prt_angortho (* prt_fator 1.0))
		  prt_ale_c3 (polar prt_ale_c2 (+ prt_angbase pi) (* prt_fator 5.0))
		  prt_ale_c4 (polar prt_ale_c3 (+ prt_angortho pi) (* prt_fator 1.0))
	    )
	    (command "._line" "_non" prt_ale_c1 "_non" prt_ale_c2 "_non" prt_ale_c3 "_non" prt_ale_c4 "")
	    (setq prt_ale_d1 (polar prt_cxi7 prt_angbase (* 1.0 prt_fator))
		  prt_ale_d2 (polar prt_ale_d1 prt_angortho (* prt_fator 1.0))
		  prt_ale_d3 (polar prt_ale_d2 prt_angbase (* prt_fator 5.0))
		  prt_ale_d4 (polar prt_ale_d3 (+ prt_angortho pi) (* prt_fator 1.0))
	    )
	    (command "._line" "_non" prt_ale_d1 "_non" prt_ale_d2 "_non" prt_ale_d3 "_non" prt_ale_d4 "")
	  )
	)
	;porta interna
	(progn
	  (if (= prt_pt21_cxi "prt_21_cxi_01")
	    ;caixiho simples
	    (progn
	      (setq prt_ale_c1 (polar prt_cxi2 (+ prt_angbase pi) (* prt_fator 1.0))
		    prt_ale_c2 (polar prt_ale_c1 prt_angortho (* prt_fator 1.0))
		    prt_ale_c3 (polar prt_ale_c2 (+ prt_angbase pi) (* prt_fator 5.0))
		    prt_ale_c4 (polar prt_ale_c3 (+ prt_angortho pi) (* prt_fator 1.0))
	      )
	      (command "._line" "_non" prt_ale_c1 "_non" prt_ale_c2 "_non" prt_ale_c3 "_non" prt_ale_c4 "")
	      (setq prt_ale_d1 (polar prt_cxi6 prt_angbase (* prt_fator 1.0))
		    prt_ale_d2 (polar prt_ale_d1 prt_angortho (* prt_fator 1.0))
		    prt_ale_d3 (polar prt_ale_d2 prt_angbase (* prt_fator 5.0))
		    prt_ale_d4 (polar prt_ale_d3 (+ prt_angortho pi) (* prt_fator 1.0))
	      )
	      (command "._line" "_non" prt_ale_d1 "_non" prt_ale_d2 "_non" prt_ale_d3 "_non" prt_ale_d4 "")
	    )
	    ;caixilho detalhado
	    (progn
	      (setq prt_ale_c1 (polar prt_cxi4 (+ prt_angbase pi) (* prt_fator 1.0))
		    prt_ale_c2 (polar prt_ale_c1 prt_angortho (* prt_fator 1.0))
		    prt_ale_c3 (polar prt_ale_c2 (+ prt_angbase pi) (* prt_fator 5.0))
		    prt_ale_c4 (polar prt_ale_c3 (+ prt_angortho pi) (* prt_fator 1.0))
	      )
	      (command "._line" "_non" prt_ale_c1 "_non" prt_ale_c2 "_non" prt_ale_c3 "_non" prt_ale_c4 "")
	      (setq prt_ale_d1 (polar prt_cxi8 prt_angbase (* prt_fator 1.0))
		    prt_ale_d2 (polar prt_ale_d1 prt_angortho (* prt_fator 1.0))
		    prt_ale_d3 (polar prt_ale_d2 prt_angbase (* prt_fator 5.0))
		    prt_ale_d4 (polar prt_ale_d3 (+ prt_angortho pi) (* prt_fator 1.0))
	      )
	      (command "._line" "_non" prt_ale_d1 "_non" prt_ale_d2 "_non" prt_ale_d3 "_non" prt_ale_d4 "")
	    )
	  )
	)
      )
    )
  )
)


;*****************************************
;Desenho das Soleiras                     
;*****************************************
(defun prt_drw21_soleira ()
  (cn7_verylayer prt_layc_sol 7)
  (setvar "cecolor" prt_layc_soc)
  ;soleira interna
  (if (= prt_pt21_soi "1")
    (progn
      (command "._line" "_non" prt_sol_i1 "_non" prt_sol_i2 "")
      (if (= prt_pt21_pos "prt_21_pos_02")
	(command "._line" "_non" prt_sol_i3  "_non" prt_sol_i4 "")
      )
    )
  )
  (if (= prt_pt21_soe "1")
    (command "._line" "_non" prt_sol_e1 "_non" prt_sol_e2 "")
  )
)

;*****************************************
;Desenho de Portas                        
;*****************************************
(defun prt_drw21_porta ()
  (setq prt_porta2 (polar prt_porta1 (+ prt_angortho pi) (* prt_fator (distof prt_pt21_poe)))
	prt_porta3 (polar prt_porta2 prt_angbase prt_larg)
	prt_porta4 (polar prt_porta1 prt_angbase prt_larg)
  )
  (cn7_verylayer prt_layc_pol 7)
  (setvar "cecolor" prt_layc_poc)
  (command "._pline"  "_non" prt_porta1 "_non" prt_porta2  "_non" prt_porta3 "_non" prt_porta4 "_c")
)


;*****************************************
;Desenho de Caixilho                      
;*****************************************

;caso 01 - porta externa
(defun prt_drw21a_caixilho ()
  (cn7_verylayer prt_layc_cxl 7)
  (setvar "cecolor" prt_layc_cxc)
  (if (/= 0.0 prt_caix)
    (progn
      (if (= prt_pt21_cxi "prt_21_cxi_01")
	(progn
	  (setq prt_cxi1 (polar prt_brk1 (+ prt_angortho pi) (* prt_fator (distof prt_pt21_poe)))
		prt_cxi2 (polar prt_cxi1 prt_angbase prt_caix)
		prt_cxi3 (polar prt_brk3 prt_angbase prt_caix)
		prt_cxi4 (polar prt_brk2 (+ pi prt_angbase) prt_caix)
		prt_cxi5 (polar prt_brk4 (+ pi prt_angbase) prt_caix)
		)
	  (command "._pline"  "_non" prt_brk1 "_non" prt_cxi1  "_non" prt_cxi2  "_non" prt_cxi3  "_non" prt_brk3 ""
		   "._pline"  "_non" prt_brk2 "_non" prt_cxi4  "_non" prt_cxi5 "_non" prt_brk4 ""
          )
	  (setq prt_porta1 (polar prt_brk1 prt_angbase (/ prt_larg 2.0))
		prt_sol_i1 (polar prt_brk1 prt_angbase prt_caix)
		prt_sol_i2 prt_porta1
		prt_sol_e1 prt_cxi3
		prt_sol_e2 prt_cxi5
	  )
	)
	(progn
	  (setq prt_cxi1 (polar prt_brk1 (+ prt_angortho pi) (* prt_fator (distof prt_pt21_poe)))
		prt_cxi2 (polar prt_cxi1 prt_angbase prt_caix)
		prt_cxi3 (polar prt_cxi2 prt_angortho (* prt_fator (distof prt_pt21_poe)))
		prt_cxi4 (polar prt_cxi3 prt_angbase (* prt_fator 2.0))
		prt_cxi5 (polar prt_brk3 prt_angbase (+ prt_caix (* prt_fator 2.0)))
	  )
	  (command "._pline"  "_non" prt_brk1 "_non" prt_cxi1  "_non" prt_cxi2 "_non" prt_cxi3 "_non" prt_cxi4
		   "_non" prt_cxi5 "_non" prt_brk3 "")
	  (setq prt_cxi6 (polar prt_brk2 (+ pi prt_angbase) prt_caix)
		prt_cxi7 (polar prt_brk4 (+ pi prt_angbase) prt_caix)
	  )
	  (command "._pline"  "_non" prt_brk2 "_non" prt_cxi6 "_non" prt_cxi7 "_non" prt_brk4 "")
	  (setq prt_porta1 (polar prt_brk1 prt_angbase (/ prt_larg 2.0))
		prt_sol_i1 prt_cxi4
		prt_sol_i2 prt_porta1
		prt_sol_e1 prt_cxi5
		prt_sol_e2 prt_cxi7
	  )
        )
      )
    )
    ;se o caixilho for nulo
    (progn
	(setq prt_porta1 (polar prt_brk1 prt_angbase (/ prt_larg 2.0))
	      prt_sol_i1 prt_brk1
	      prt_sol_i2 prt_porta1
	      prt_sol_e1 prt_brk3
	      prt_sol_e2 prt_brk4
	)
    )
  )
)

;caixilho para porta interna
(defun prt_drw21b_caixilho ()
  (cn7_verylayer prt_layc_cxl 7)
  (setvar "cecolor" prt_layc_cxc)
  (if (/= 0.0 prt_caix)
    (progn
      (if (= prt_pt21_cxi "prt_21_cxi_01")
	(progn
	  (setq prt_cxi1 (polar prt_brk1 prt_angbase prt_caix)
		prt_cxi2 (polar prt_brk3 prt_angbase prt_caix)
		prt_cxi3 (polar prt_brk5 (+ pi prt_angbase) prt_caix)
		prt_cxi4 (polar prt_brk6 (+ pi prt_angbase) prt_caix)
		prt_cxi5 (polar prt_brk7 (+ pi prt_angbase) prt_caix)
		prt_cxi6 (polar prt_brk4 (+ pi prt_angbase) prt_caix)
		)
	  (command "._pline" "_non" prt_brk1 "_non" prt_cxi1 "_non" prt_cxi2 "_non" prt_brk3 ""
		   "._pline" "_non" prt_brk5 "_non" prt_cxi3 "_non" prt_cxi4 ""
		   "._pline" "_non" prt_brk7 "_non" prt_cxi5 "_non" prt_cxi6 "_non" prt_brk4 ""
          )
	  (setq prt_porta1a (polar prt_brk1 prt_angbase (/ prt_larg 2.0))
		prt_porta1 (polar prt_porta1a prt_angortho (* prt_fator (distof prt_pt21_poe)))
		prt_sol_i1 prt_cxi1
		prt_sol_i2 prt_porta1a
		prt_sol_i3 (polar prt_porta1a prt_angbase prt_larg)
		prt_sol_i4 prt_cxi3
		prt_sol_e1 prt_cxi2
		prt_sol_e2 prt_cxi6
	  )
	)
	(progn
	  (setq prt_cxi1 (polar prt_brk1 prt_angbase prt_caix)
		prt_cxi2 (polar prt_cxi1 prt_angortho (* prt_fator (+ 1.5 (distof prt_pt21_poe))))
		prt_cxi3 (polar prt_cxi2 prt_angbase (* prt_fator 2.0))
		prt_cxi4 (polar prt_brk3 prt_angbase (+ prt_caix (* prt_fator 2.0)))
	  )
	  (command "._pline"  "_non" prt_brk1 "_non" prt_cxi1  "_non" prt_cxi2 "_non" prt_cxi3 "_non" prt_cxi4
		   "_non" prt_brk3 "")
	  (setq prt_cxi5 (polar prt_brk5 (+ pi prt_angbase) prt_caix)
		prt_cxi6 (polar prt_brk6 (+ pi prt_angbase) prt_caix)
		prt_cxi7 (polar prt_brk7 (+ pi prt_angbase) prt_caix)
		prt_cxi8 (polar prt_brk4 (+ pi prt_angbase) prt_caix)
		)
	  (command "._pline" "_non" prt_brk5 "_non" prt_cxi5 "_non" prt_cxi6 ""
		   "._pline" "_non" prt_brk7 "_non" prt_cxi7 "_non" prt_cxi8 "_non" prt_brk4 ""
          )
	  (setq prt_porta1a (polar prt_brk1 prt_angbase (/ prt_larg 2.0))
		prt_porta1 (polar prt_porta1a prt_angortho (* prt_fator (distof prt_pt21_poe)))
		prt_sol_i1 prt_cxi1
		prt_sol_i2 prt_porta1a
		prt_sol_i3 (polar prt_porta1a prt_angbase prt_larg)
		prt_sol_i4 prt_cxi5
		prt_sol_e1 prt_cxi4
		prt_sol_e2 prt_cxi8
	  )
        )
      )
    )
    ;se o caixilho for nulo
    (progn
      (setq prt_porta1a (polar prt_brk1 prt_angbase (/ prt_larg 2.0))
	    prt_porta1 (polar prt_porta1a prt_angortho (* prt_fator (distof prt_pt21_poe)))
	    prt_sol_i1 prt_brk1
	    prt_sol_i2 prt_porta1a
	    prt_sol_i3 (polar prt_porta1a prt_angbase prt_larg)
	    prt_sol_i4 prt_brk5
	    prt_sol_e1 prt_brk3
	    prt_sol_e2 prt_brk4
	  )
    )
  )
)

;openfree especial para porta 21
(defun prt_drw21_openfree ()
  ;conversão de dados para numerais
  (prt_larg_file)
;;;  (setq prt_larg (* prt_fator (distof (nth (fix (distof prt_var_larg)) prt_larg_list))))
  (if (= prt_var_lrad "prt_larg_radio1")
    (setq prt_larg (* prt_fator (distof (nth (fix (distof prt_var_larg)) prt_larg_list))))
    (setq prt_larg (* prt_fator (distof prt_var_lvao)))
  )
  (prt_halt_file)
  (setq prt_halt (* prt_fator (distof (nth (fix (distof prt_var_halt)) prt_halt_list)))
	prt_afas (* prt_fator (distof prt_var_afas))
	prt_wall (* prt_fator (distof prt_var_wall))
	prt_caix (* prt_fator (distof prt_var_caix))
  )
  ;clica na parede
  (prompt "\nSelecione a parede interna...")
  (setq prt_entsel (entsel)
	prt_ent1 (car prt_entsel)
	prt_ent1_type (cdr (assoc 0 (entget prt_ent1)))
	prt_pt0 (nth 0 (cdr prt_entsel))
	prt_ptt1 (cdr (assoc 10 (entget prt_ent1)))
	prt_ptt2 (cdr (assoc 11 (entget prt_ent1)))
	prt_wall_layer (cdr (assoc 8 (entget prt_ent1)))
  )
  (if (/= "LINE" prt_ent1_type)
    (progn
      (alert "A entidade Selecionada não é uma 'LINE'.\nPOLYLINES devem ser explodidas\npara usar este comando...")
      (prt_drw21_openfree)
    )
  )
  (if (<= (distance prt_pt0 prt_ptt1) (distance prt_pt0 prt_ptt2))
    (setq prt_pt1 prt_ptt1 prt_pt2 prt_ptt2 prt_code 1)
    (setq prt_pt1 prt_ptt2 prt_pt2 prt_ptt1 prt_code 2)
  )
  (setq prt_angbase (angle prt_pt1 prt_pt2))
  ;verifica o posicionamento para determinar os pontos de quebra
  (if (= prt_var_posi "prt_center")
    (setq prt_doll (/ (- (distance prt_pt1 prt_pt2) prt_larg (* 2 prt_caix)) 2))
    (setq prt_doll prt_afas)
  )
  (setq
	prt_brk1 (polar prt_pt1 prt_angbase prt_doll)
	prt_brk2 (polar prt_brk1 prt_angbase (+ prt_larg (* 2 prt_caix)))
  )
  (if (= prt_code 1)
    (setq prt_brk3a (polar prt_brk1 (- prt_angbase (/ pi 2)) prt_wall)
	  prt_brk3b (polar prt_brk1 (+ prt_angbase (/ pi 2)) prt_wall)
	  prt_brk4a (polar prt_brk2 (- prt_angbase (/ pi 2)) prt_wall)
	  prt_brk4b (polar prt_brk2 (+ prt_angbase (/ pi 2)) prt_wall)
    )
    (setq prt_brk3a (polar prt_brk1 (+ prt_angbase (/ pi 2)) prt_wall)
  	  prt_brk3b (polar prt_brk1 (- prt_angbase (/ pi 2)) prt_wall)
	  prt_brk4a (polar prt_brk2 (+ prt_angbase (/ pi 2)) prt_wall)
	  prt_brk4b (polar prt_brk2 (- prt_angbase (/ pi 2)) prt_wall)
    )
  )
  (if (/= nil (ssget "_f" (list prt_brk3a prt_brk4a) (list (cons 8 prt_wall_layer))))
    (progn
      (setq prt_brk3 prt_brk3a prt_brk4 prt_brk4a prt_xcode 1)
      (setq prt_brkm (polar prt_brk3 (angle prt_brk3 prt_brk4) (/ (distance prt_brk3 prt_brk4) 2)))
      (if (= nil (ssget "c" prt_brkm prt_brkm))
	(progn
	  (setq prt_brk3 prt_brk3b prt_brk4 prt_brk4b)
	  (setq prt_brkm (polar prt_brk3 (angle prt_brk3 prt_brk4) (/ (distance prt_brk3 prt_brk4) 2))
		prt_xcode 2)
	)
      )
    )
    (progn
      (setq prt_brk3 prt_brk3b prt_brk4 prt_brk4b prt_xcode 2)
      (setq prt_brkm (polar prt_brk3 (angle prt_brk3 prt_brk4) (/ (distance prt_brk3 prt_brk4) 2)))
      (if (= nil (ssget "c" prt_brkm prt_brkm))
	(progn
	  (setq prt_brk3 prt_brk3a prt_brk4 prt_brk4a)
	  (setq prt_brkm (polar prt_brk3 (angle prt_brk3 prt_brk4) (/ (distance prt_brk3 prt_brk4) 2))
		prt_xcode 4)
	)
      )
    )
  )
  (setq prt_angortho (angle prt_brk1 prt_brk3))
  (command "._undo" "_m")
  (setq colmo (getvar "cecolor"))
  (if (= prt_pt21_pos "prt_21_pos_01")
    (progn
      (command "._break" prt_ent1 "_non" prt_brk1 "_non" prt_brk2)
      (command "._break" (ssget "c" prt_brkm prt_brkm) "_non" prt_brk3 "_non" prt_brk4)
      (command "._layer" "_s" prt_wall_layer "")
      (command "._line" "_non" prt_brk1 "_non" prt_brk3 ""
	       "._line" "_non" prt_brk2 "_non" prt_brk4 "")
    )
    (progn
      (setq prt_brk5 (polar prt_brk2 prt_angbase (+ prt_larg (* 2.0 prt_caix)))
	    prt_brk6 (polar prt_brk5 prt_angortho (* prt_fator (+ 1.5 (distof prt_pt21_poe))))
	    prt_brk7 (polar prt_brk6 (+ prt_angbase pi) (+ prt_larg (* 2.0 prt_caix)))
      )
      (command "._break" prt_ent1 "_non" prt_brk1 "_non" prt_brk5)
      (command "._break" (ssget "c" prt_brkm prt_brkm) "_non" prt_brk3 "_non" prt_brk4)
      (command "._layer" "_s" prt_wall_layer "")
      (command "._line" "_non" prt_brk1 "_non" prt_brk3 ""
	       "._line" "_non" prt_brk5 "_non" prt_brk6 "_non" prt_brk7 "_non" prt_brk4 "")
    )
  )
)



;***********************************
;Porta Tipo 22                      
;Parte 01 - Configuração            
;***********************************
(defun prt_cfg_22 ()
  (prt_pt22_file)
  (setq dcl_id (load_dialog (strcat cnp_root "/lisp/cadnorma.dcl")))
  (if (not (new_dialog "prt_cfg_p22" dcl_id)) (exit))
  (set_tile "prt_descr" "Porta Deslizante Dupla ('de Correr')")
  ;slide de tipo
  (setq x (dimx_tile "prt_22_slide")
	y (dimy_tile "prt_22_slide")
  )
  (start_image "prt_22_slide")
  (fill_image 0 0 x y -2)
  (slide_image 0 0 x y (strcat cnp_root "/slides/prt_" prt_var_tipo ".sld"))
  (end_image)
  ;espessura da porta
  (set_tile "prt_22_poe_edit" prt_pt22_poe)
  (action_tile "prt_22_poe_edit" "(prt_22_poe_edit_act)")
  (action_tile "prt_22_poe_pick" "(done_dialog 2)")
  ;soleira
  (if (= "1" prt_pt22_soi) (set_tile "prt_22_solint"  "1"))
  (action_tile "prt_22_solint"  "(setq prt_pt22_soi $value)")
  (if (= "1" prt_pt22_soe) (set_tile "prt_22_solext"  "1"))
  (action_tile "prt_22_solext"  "(setq prt_pt22_soe $value)")
  ;alisares
  (if (= "1" prt_pt22_ali) (set_tile "prt_22_aliint"  "1"))
  (action_tile "prt_22_aliint"  "(setq prt_pt22_ali $value)")
  (if (= "1" prt_pt22_ale) (set_tile "prt_22_aliext"  "1"))
  (action_tile "prt_22_aliext"  "(setq prt_pt22_ale $value)")
  ;tipo de posicionamento (interna ou externa)
  (setq x (dimx_tile "prt_22_possld_01")
	y (dimy_tile "prt_22_possld_01")
  )
  (start_image "prt_22_possld_01")
  (fill_image 0 0 x y -2)
  (slide_image 0 0 x y (strcat cnp_root "/slides/prt_pos_2201.sld"))
  (end_image)
  (setq x (dimx_tile "prt_22_possld_02")
	y (dimy_tile "prt_22_possld_02")
  )
  (start_image "prt_22_possld_02")
  (fill_image 0 0 x y -2)
  (slide_image 0 0 x y (strcat cnp_root "/slides/prt_pos_2202.sld"))
  (end_image)
  (action_tile "prt_22_possld_01" "(prt_22_possld_act)")
  (action_tile "prt_22_possld_02" "(prt_22_possld_act)")
  (cond
    ((= prt_pt22_pos "prt_22_pos_01") (set_tile "prt_22_pos_01" "1"))
    ((= prt_pt22_pos "prt_22_pos_02") (set_tile "prt_22_pos_02" "1"))
  )
  (action_tile "prt_22_pos_01" "(prt_22_pos_act)")
  (action_tile "prt_22_pos_02" "(prt_22_pos_act)")
  ;ok_cancel
  (action_tile "cancel" "(done_dialog 0)")
  (action_tile "accept" "(done_dialog 1)")
  ;start_dialog
  (setq prt_22_id (start_dialog))
  (unload_dialog dcl_id)
  (if (= prt_22_id 1) (prt_pt22_writefile))
  (if (= prt_22_id 2) (prt_22_poe_button_act))
)

;radio_buttons para posicionamento
(defun prt_22_pos_act ()
  (setq prt_pt22_pos $key)
  (cond
    ((= prt_pt22_pos "prt_22_pos_01")
     (set_tile "prt_22_pos_01" "1")
     (set_tile "prt_22_pos_02" "0")
    )
    ((= prt_pt22_pos "prt_22_pos_02")
     (set_tile "prt_22_pos_01" "0")
     (set_tile "prt_22_pos_02" "1")
    )
  )
)

;slides de tipo de posicionamento
(defun prt_22_possld_act ()
  (setq prt_pt22_possld $key)
  (cond
    ((= prt_pt22_possld "prt_22_possld_01")
     (setq prt_pt22_pos "prt_22_pos_01")
     (set_tile "prt_22_pos_01" "1")
     (set_tile "prt_22_pos_02" "0")
    )
    ((= prt_pt22_possld "prt_22_possld_02")
     (setq prt_pt22_pos "prt_22_pos_02")
     (set_tile "prt_22_pos_01" "0")
     (set_tile "prt_22_pos_02" "1")
    )
  )
)


;Espessura por Pick Points
(defun prt_22_poe_button_act ()
  (prt_pt22_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt22_poe (rtos new_dist 2 2))
      (prt_pt22_writefile)
    )
  )
  (prt_cfg_22)
)


;verifica se o valor de espessura entrado é válido
(defun prt_22_poe_edit_act ()
  (setq prt_var_newpoe $value)
  (if (distof prt_var_newpoe)
    (progn
      (setq prt_pt22_poe prt_var_newpoe)
      (prt_pt22_writefile)
    )
    (progn
      (alert "Valor Inválido!")
      (set_tile "prt_22_poe_edit" prt_pt22_poe)
      (mode_tile "prt_22_poe_edit" 2)
    )
  )
)  

;lê os dados iniciais da DCL no arquivo de dados
(defun prt_pt22_file ()
  (if (findfile (strcat cnp_root "/config/prt_pt22.txt"))
    (prt_pt22_readfile)
    (progn
      (setq file (open (strcat cnp_root "/config/prt_pt22.txt") "w" "utf8"))
      (write-line "3" file)
      (write-line "1" file)
      (write-line "1" file)      
      (write-line "1" file)
      (write-line "1" file)
      (write-line "prt_22_pos_01" file)
      (close file)
      (prt_pt22_readfile)
    )
  )
)


;função que lê o arquivo de dados
(defun prt_pt22_readfile ()
  (setq	file (open (strcat cnp_root "/config/prt_pt22.txt") "r" "utf8"))
  (setq	prt_pt22_poe (read-line file))
  (setq	prt_pt22_soi (read-line file))
  (setq	prt_pt22_soe (read-line file))
  (setq	prt_pt22_ali (read-line file))
  (setq	prt_pt22_ale (read-line file))
  (setq	prt_pt22_pos (read-line file))
  (close file)
)

;função que escreve o arquivo de dados
(defun prt_pt22_writefile ()
  (setq	file (open (strcat cnp_root "/config/prt_pt22.txt") "w" "utf8"))
  (write-line prt_pt22_poe file)
  (write-line prt_pt22_soi file)
  (write-line prt_pt22_soe file)
  (write-line prt_pt22_ali file)
  (write-line prt_pt22_ale file)
  (write-line prt_pt22_pos file)
  (close file)
)

;Desenha a porta
(defun prt_drw22 ()
  (cn7_init)
  (guarda '("blipmode" "cecolor" "celtype" "clayer" "cmdecho" "orthomode"
          "textstyle" "luprec" "osmode" ))
  (setvar "cecolor" "bylayer")
  (prt_pt22_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_drw22_openfree)
  (if (= prt_pt22_pos "prt_22_pos_01")
    (prt_drw22a_caixilho)
    (prt_drw22b_caixilho)
  )
  (prt_drw22_porta)
  (prt_drw22_soleira)
  (if (/= 0.0 prt_caix)
    (prt_drw22_alisar)
  )
  (prt_drw22_seta)
  (devolve)
  (prompt "\nUse o comando <UB> para retornar... ")
)

;*****************************************
;Desenho das Setas                        
;*****************************************
(defun prt_drw22_seta ()
  (cn7_verylayer "porta_seta" 1)
  (if (= prt_pt22_pos "prt_22_pos_01")
    (setq prt_seta (polar prt_porta2 prt_angbase (/ prt_larg 2.0))
	  prt_seta (polar prt_seta (+ pi prt_angortho) (* prt_fator 5))
    )
    (setq prt_seta (polar prt_porta1a prt_angbase (/ prt_larg 2.0))
	  prt_seta (polar prt_seta (+ pi prt_angortho) (* prt_fator 5))
    )
  )
  (command "._insert" (strcat cnp_root "/blocos/prt_seta") "_s" prt_blkscl "_non" prt_seta (* 180 (/ prt_angbase pi))
	   "._mirror" (entlast) "" "_non" prt_mid1 "_non" prt_p12_mid2 "_n")
)

;*****************************************
;Desenho das Alisares                     
;*****************************************
(defun prt_drw22_alisar ()
  (cn7_verylayer prt_layc_all 7)
  (setvar "cecolor" prt_layc_alc)
  ;alisares internos
  (if (= "1" prt_pt22_ali)
    ;porta externa
    (if (= prt_pt22_pos "prt_22_pos_02")
      (progn
	(setq prt_ali_a1 (polar prt_cxi1 (+ prt_angbase pi) (* prt_fator 1.0))
	      prt_ali_a2 (polar prt_ali_a1 (+ prt_angortho pi) (* prt_fator 1.0))
	      prt_ali_a3 (polar prt_ali_a2 (+ prt_angbase pi) (* prt_fator 5.0))
	      prt_ali_a4 (polar prt_ali_a3 prt_angortho (* prt_fator 1.0))
	)
	(command "._line" "_non" prt_ali_a1 "_non" prt_ali_a2 "_non" prt_ali_a3 "_non" prt_ali_a4 "")
	(setq prt_ali_b1 (polar prt_cxi5 prt_angbase (* prt_fator 1.0))
	      prt_ali_b2 (polar prt_ali_b1 (+ prt_angortho pi) (* prt_fator 1.0))
	      prt_ali_b3 (polar prt_ali_b2 prt_angbase (* prt_fator 5.0))
	      prt_ali_b4 (polar prt_ali_b3 prt_angortho (* prt_fator 1.0))
	)
	(command "._line" "_non" prt_ali_b1 "_non" prt_ali_b2 "_non" prt_ali_b3 "_non" prt_ali_b4 "")
      )
    )
  )
  ;alisares externos
  (if (= "1" prt_pt22_ale)
      ;porta externa
      (if (= prt_pt22_pos "prt_22_pos_01")
	(progn
	  (setq prt_ale_c1 (polar prt_cxi2 (+ prt_angbase pi) (* 1.0 prt_fator))
		prt_ale_c2 (polar prt_ale_c1 prt_angortho (* prt_fator 1.0))
		prt_ale_c3 (polar prt_ale_c2 (+ prt_angbase pi) (* prt_fator 5.0))
		prt_ale_c4 (polar prt_ale_c3 (+ prt_angortho pi) (* prt_fator 1.0))
	  )
	  (command "._line" "_non" prt_ale_c1 "_non" prt_ale_c2 "_non" prt_ale_c3 "_non" prt_ale_c4 "")
	  (setq prt_ale_d1 (polar prt_cxi4 prt_angbase (* 1.0 prt_fator))
		prt_ale_d2 (polar prt_ale_d1 prt_angortho (* prt_fator 1.0))
		prt_ale_d3 (polar prt_ale_d2 prt_angbase (* prt_fator 5.0))
		prt_ale_d4 (polar prt_ale_d3 (+ prt_angortho pi) (* prt_fator 1.0))
	  )
	  (command "._line" "_non" prt_ale_d1 "_non" prt_ale_d2 "_non" prt_ale_d3 "_non" prt_ale_d4 "")
	)
	;porta interna
	(progn
	  (setq prt_ale_c1 (polar prt_cxi4 (+ prt_angbase pi) (* prt_fator 1.0))
		prt_ale_c2 (polar prt_ale_c1 prt_angortho (* prt_fator 1.0))
		prt_ale_c3 (polar prt_ale_c2 (+ prt_angbase pi) (* prt_fator 5.0))
		prt_ale_c4 (polar prt_ale_c3 (+ prt_angortho pi) (* prt_fator 1.0))
	  )
	  (command "._line" "_non" prt_ale_c1 "_non" prt_ale_c2 "_non" prt_ale_c3 "_non" prt_ale_c4 "")
	  (setq prt_ale_d1 (polar prt_cxi8 prt_angbase (* prt_fator 1.0))
		prt_ale_d2 (polar prt_ale_d1 prt_angortho (* prt_fator 1.0))
		prt_ale_d3 (polar prt_ale_d2 prt_angbase (* prt_fator 5.0))
		prt_ale_d4 (polar prt_ale_d3 (+ prt_angortho pi) (* prt_fator 1.0))
	  )
	  (command "._line" "_non" prt_ale_d1 "_non" prt_ale_d2 "_non" prt_ale_d3 "_non" prt_ale_d4 "")
	)
      )
  )
)


;*****************************************
;Desenho das Soleiras                     
;*****************************************
(defun prt_drw22_soleira ()
  (cn7_verylayer prt_layc_sol 7)
  (setvar "cecolor" prt_layc_soc)
  ;soleira interna
  (if (= prt_pt22_soi "1")
    (if (= prt_pt22_pos "prt_22_pos_01")
      (command "._line" "_non" prt_sol_i1 "_non" prt_sol_i2 "")
      (progn
	(command "._line" "_non" prt_sol_i1 "_non" prt_sol_i2 ""
		 "._line" "_non" prt_sol_i3 "_non" prt_sol_i4 ""
		 "._line" "_non" prt_sol_i5 "_non" prt_sol_i6 ""
	)
      )
    )
  )
  (if (= prt_pt22_soe "1")
    (command "._line" "_non" prt_sol_e1 "_non" prt_sol_e2 "")
  )
)

;*****************************************
;Desenho de Portas                        
;*****************************************
(defun prt_drw22_porta ()
  (setq prt_porta2 (polar prt_porta1 (+ prt_angortho pi) (* prt_fator (distof prt_pt22_poe)))
	prt_porta3 (polar prt_porta2 prt_angbase prt_larg)
	prt_porta4 (polar prt_porta1 prt_angbase prt_larg)
  )
  (cn7_verylayer prt_layc_pol 7)
  (setvar "cecolor" prt_layc_poc)
  (command "._pline"  "_non" prt_porta1 "_non" prt_porta2  "_non" prt_porta3 "_non" prt_porta4 "_c"
	   "._mirror" (entlast) "" "_non" prt_mid1 "_non" prt_mid2 "_n"
  )
)


;*****************************************
;Desenho de Caixilho                      
;*****************************************

;caso 01 - porta externa
(defun prt_drw22a_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_brk3 prt_angbase prt_caix)
	    prt_cxi3 (polar prt_brk2 (+ pi prt_angbase) prt_caix)
	    prt_cxi4 (polar prt_brk4 (+ pi prt_angbase) prt_caix)
      )
      (command "._pline"  "_non" prt_brk1 "_non" prt_cxi1  "_non" prt_cxi2 "_non" prt_brk3 ""
	       "._pline"  "_non" prt_brk2 "_non" prt_cxi3  "_non" prt_cxi4 "_non" prt_brk4 ""
      )
      (setq prt_porta1 (polar prt_brk1 (+ pi prt_angbase) (/ prt_larg 2.0))
	    prt_sol_i1 (polar prt_brk1 prt_angbase (/ prt_larg 2.0))
	    prt_sol_i2 (polar prt_brk2 (+ pi prt_angbase) (/ prt_larg 2.0))
	    prt_sol_e1 prt_cxi2
	    prt_sol_e2 prt_cxi4
      )
    )
    ;se o caixilho for nulo
    (progn
	(setq prt_porta1 (polar prt_brk1 (+ pi prt_angbase) (/ prt_larg 2.0))
	    prt_sol_i1 (polar prt_brk1 prt_angbase (/ prt_larg 2.0))
	    prt_sol_i2 (polar prt_brk2 (+ pi prt_angbase) (/ prt_larg 2.0))
	    prt_sol_e1 prt_brk3
	    prt_sol_e2 prt_brk4
      )
    )
  )
)

;caixilho para porta interna
(defun prt_drw22b_caixilho ()
  (cn7_verylayer prt_layc_cxl 7)
  (setvar "cecolor" prt_layc_cxc)
  (if (/= 0.0 prt_caix)
    (progn
      (setq prt_cxi1 (polar prt_brk5 prt_angbase prt_caix)
	    prt_cxi2 (polar prt_brk6 prt_angbase prt_caix)
	    prt_cxi3 (polar prt_brk7 prt_angbase prt_caix)
	    prt_cxi4 (polar prt_brk3 prt_angbase prt_caix)
	    prt_cxi5 (polar prt_brk8 (+ pi prt_angbase) prt_caix)
	    prt_cxi6 (polar prt_brk9 (+ pi prt_angbase) prt_caix)
	    prt_cxi7 (polar prt_brk0 (+ pi prt_angbase) prt_caix)
	    prt_cxi8 (polar prt_brk4 (+ pi prt_angbase) prt_caix)
      )
      (command "._pline" "_non" prt_brk5 "_non" prt_cxi1 "_non" prt_cxi2 ""
	       "._pline" "_non" prt_brk7 "_non" prt_cxi3 "_non" prt_cxi4 "_non" prt_brk3 ""
	       "._pline" "_non" prt_brk8 "_non" prt_cxi5 "_non" prt_cxi6 ""
	       "._pline" "_non" prt_brk0 "_non" prt_cxi7 "_non" prt_cxi8 "_non" prt_brk4 ""
      )
      (setq prt_porta1a (polar prt_brk5 prt_angbase (/ prt_larg 2.0))
	    prt_porta1 (polar prt_porta1a prt_angortho (* prt_fator (distof prt_pt22_poe)))
	    prt_sol_i1 prt_cxi1
	    prt_sol_i2 prt_porta1a
	    prt_sol_i3 prt_cxi5
	    prt_sol_i4 (polar prt_brk8 (+ pi prt_angbase) (/ prt_larg 2.0))
	    prt_sol_i5 (polar prt_sol_i2 prt_angbase prt_larg)
	    prt_sol_i6 (polar prt_sol_i4 (+ pi prt_angbase) prt_larg)
	    prt_sol_e1 prt_cxi4
	    prt_sol_e2 prt_cxi8
      )
    )
    ;se o caixilho for nulo
    (progn
      (setq prt_porta1a (polar prt_brk5 prt_angbase (/ prt_larg 2.0))
	    prt_porta1 (polar prt_porta1a prt_angortho (* prt_fator (distof prt_pt22_poe)))
	    prt_sol_i1 prt_brk5
	    prt_sol_i2 prt_porta1a
	    prt_sol_i3 prt_brk8
	    prt_sol_i4 (polar prt_brk8 (+ pi prt_angbase) (/ prt_larg 2.0))
	    prt_sol_i5 (polar prt_sol_i2 prt_angbase prt_larg)
	    prt_sol_i6 (polar prt_sol_i4 (+ pi prt_angbase) prt_larg)
	    prt_sol_e1 prt_brk3
	    prt_sol_e2 prt_brk4
	  )
    )
  )
)

;openfree especial para porta 22
(defun prt_drw22_openfree ()
  ;conversão de dados para numerais
  (prt_larg_file)
;;;  (setq prt_larg (* prt_fator (distof (nth (fix (distof prt_var_larg)) prt_larg_list))))
  (if (= prt_var_lrad "prt_larg_radio1")
    (setq prt_larg (* prt_fator (distof (nth (fix (distof prt_var_larg)) prt_larg_list))))
    (setq prt_larg (/ (* prt_fator (distof prt_var_lvao)) 2.0))
  )
  (prt_halt_file)
  (setq prt_halt (* prt_fator (distof (nth (fix (distof prt_var_halt)) prt_halt_list)))
	prt_afas (* prt_fator (distof prt_var_afas))
	prt_wall (* prt_fator (distof prt_var_wall))
	prt_caix (* prt_fator (distof prt_var_caix))
  )
  ;clica na parede
  (prompt "\nSelecione a parede interna...")
  (setq prt_entsel (entsel)
	prt_ent1 (car prt_entsel)
	prt_ent1_type (cdr (assoc 0 (entget prt_ent1)))
	prt_pt0 (nth 0 (cdr prt_entsel))
	prt_ptt1 (cdr (assoc 10 (entget prt_ent1)))
	prt_ptt2 (cdr (assoc 11 (entget prt_ent1)))
	prt_wall_layer (cdr (assoc 8 (entget prt_ent1)))
  )
  (if (/= "LINE" prt_ent1_type)
    (progn
      (alert "A entidade Selecionada não é uma 'LINE'.\nPOLYLINES devem ser explodidas\npara usar este comando...")
      (prt_drw22_openfree)
    )
  )
  (if (<= (distance prt_pt0 prt_ptt1) (distance prt_pt0 prt_ptt2))
    (setq prt_pt1 prt_ptt1 prt_pt2 prt_ptt2 prt_code 1)
    (setq prt_pt1 prt_ptt2 prt_pt2 prt_ptt1 prt_code 2)
  )
  (setq prt_angbase (angle prt_pt1 prt_pt2))
  ;verifica o posicionamento para determinar os pontos de quebra
  (if (= prt_var_posi "prt_center")
    (setq prt_doll (/ (- (distance prt_pt1 prt_pt2) (* 2 prt_larg) (* 2 prt_caix)) 2))
    (setq prt_doll prt_afas)
  )
  (setq
	prt_brk1 (polar prt_pt1 prt_angbase prt_doll)
	prt_brk2 (polar prt_brk1 prt_angbase (+ (* 2 prt_larg) (* 2 prt_caix)))
  )
  (if (= prt_code 1)
    (setq prt_brk3a (polar prt_brk1 (- prt_angbase (/ pi 2)) prt_wall)
	  prt_brk3b (polar prt_brk1 (+ prt_angbase (/ pi 2)) prt_wall)
	  prt_brk4a (polar prt_brk2 (- prt_angbase (/ pi 2)) prt_wall)
	  prt_brk4b (polar prt_brk2 (+ prt_angbase (/ pi 2)) prt_wall)
    )
    (setq prt_brk3a (polar prt_brk1 (+ prt_angbase (/ pi 2)) prt_wall)
  	  prt_brk3b (polar prt_brk1 (- prt_angbase (/ pi 2)) prt_wall)
	  prt_brk4a (polar prt_brk2 (+ prt_angbase (/ pi 2)) prt_wall)
	  prt_brk4b (polar prt_brk2 (- prt_angbase (/ pi 2)) prt_wall)
    )
  )
  (if (/= nil (ssget "_f" (list prt_brk3a prt_brk4a) (list (cons 8 prt_wall_layer))))
    (progn
      (setq prt_brk3 prt_brk3a prt_brk4 prt_brk4a prt_xcode 1)
      (setq prt_brkm (polar prt_brk3 (angle prt_brk3 prt_brk4) (/ (distance prt_brk3 prt_brk4) 2)))
      (if (= nil (ssget "c" prt_brkm prt_brkm))
	(progn
	  (setq prt_brk3 prt_brk3b prt_brk4 prt_brk4b)
	  (setq prt_brkm (polar prt_brk3 (angle prt_brk3 prt_brk4) (/ (distance prt_brk3 prt_brk4) 2))
		prt_xcode 2)
	)
      )
    )
    (progn
      (setq prt_brk3 prt_brk3b prt_brk4 prt_brk4b prt_xcode 2)
      (setq prt_brkm (polar prt_brk3 (angle prt_brk3 prt_brk4) (/ (distance prt_brk3 prt_brk4) 2)))
      (if (= nil (ssget "c" prt_brkm prt_brkm))
	(progn
	  (setq prt_brk3 prt_brk3a prt_brk4 prt_brk4a)
	  (setq prt_brkm (polar prt_brk3 (angle prt_brk3 prt_brk4) (/ (distance prt_brk3 prt_brk4) 2))
		prt_xcode 4)
	)
      )
    )
  )
  (setq prt_angortho (angle prt_brk1 prt_brk3))
  (command "._undo" "_m")
  (setq colmo (getvar "cecolor"))
  (if (= prt_pt22_pos "prt_22_pos_01")
    ;porta externa
    (progn
      (command "._break" prt_ent1 "_non" prt_brk1 "_non" prt_brk2)
      (command "._break" (ssget "c" prt_brkm prt_brkm) "_non" prt_brk3 "_non" prt_brk4)
      (command "._layer" "_s" prt_wall_layer "")
      (command "._line" "_non" prt_brk1 "_non" prt_brk3 ""
	       "._line" "_non" prt_brk2 "_non" prt_brk4 "")
    )
    ;porta interna
    (progn
      (setq prt_brk5 (polar prt_brk1 (+ prt_angbase pi) (+ prt_larg (* 2.0 prt_caix)))
	    prt_brk6 (polar prt_brk5 prt_angortho (* prt_fator (+ 1.5 (distof prt_pt22_poe))))
	    prt_brk7 (polar prt_brk6 prt_angbase (+ prt_larg (* 2.0 prt_caix)))
	    prt_brk8 (polar prt_brk2 prt_angbase (+ prt_larg (* 2.0 prt_caix)))
	    prt_brk9 (polar prt_brk8 prt_angortho (* prt_fator (+ 1.5 (distof prt_pt22_poe))))
	    prt_brk0 (polar prt_brk9 (+ prt_angbase pi) (+ prt_larg (* 2.0 prt_caix)))
      )
      (command "._break" prt_ent1 "_non" prt_brk5 "_non" prt_brk8)
      (command "._break" (ssget "c" prt_brkm prt_brkm) "_non" prt_brk3 "_non" prt_brk4)
      (command "._layer" "_s" prt_wall_layer "")
      (command "._line" "_non" prt_brk5 "_non" prt_brk6 "_non" prt_brk7 "_non" prt_brk3 ""
	       "._line" "_non" prt_brk8 "_non" prt_brk9 "_non" prt_brk0 "_non" prt_brk4 "")
    )
  )
  (setq prt_mid1 (polar prt_brk1 prt_angbase (/ (distance prt_brk1 prt_brk2) 2.0))
	prt_mid2 (polar prt_brk3 prt_angbase (/ (distance prt_brk3 prt_brk4) 2.0))
  )
)



;***********************************
;Porta Tipo 23                      
;Parte 01 - Configuração            
;***********************************
(defun prt_cfg_23 ()
  (prt_pt23_file)
  (setq dcl_id (load_dialog (strcat cnp_root "/lisp/cadnorma.dcl")))
  (if (not (new_dialog "prt_cfg_p23" dcl_id)) (exit))
  (set_tile "prt_descr" "Porta Sanfonada")
  ;slide de tipo
  (setq x (dimx_tile "prt_23_slide")
	y (dimy_tile "prt_23_slide")
  )
  (start_image "prt_23_slide")
  (fill_image 0 0 x y -2)
  (slide_image 0 0 x y (strcat cnp_root "/slides/prt_" prt_var_tipo ".sld"))
  (end_image)
  ;soleira
  (if (= "1" prt_pt23_soi) (set_tile "prt_23_solint"  "1"))
  (action_tile "prt_23_solint"  "(setq prt_pt23_soi $value)")
  (if (= "1" prt_pt23_soe) (set_tile "prt_23_solext"  "1"))
  (action_tile "prt_23_solext"  "(setq prt_pt23_soe $value)")
  ;alisares
  (if (= "1" prt_pt23_ali) (set_tile "prt_23_aliint"  "1"))
  (action_tile "prt_23_aliint"  "(setq prt_pt23_ali $value)")
  (if (= "1" prt_pt23_ale) (set_tile "prt_23_aliext"  "1"))
  (action_tile "prt_23_aliext"  "(setq prt_pt23_ale $value)")
  ;ok_cancel
  (action_tile "cancel" "(done_dialog 0)")
  (action_tile "accept" "(done_dialog 1)")
  ;start_dialog
  (setq prt_23_id (start_dialog))
  (unload_dialog dcl_id)
  (if (= prt_23_id 1) (prt_pt23_writefile))
  (if (= prt_23_id 2) (prt_23_poe_button_act))
)

;radio_buttons para caixilho
(defun prt_23_cxi_act ()
  (setq prt_pt23_cxi $key)
  (cond
    ((= prt_pt23_cxi "prt_23_cxi_01")
     (set_tile "prt_23_cxi_01" "1")
     (set_tile "prt_23_cxi_02" "0")
    )
    ((= prt_pt23_cxi "prt_23_cxi_02")
     (set_tile "prt_23_cxi_01" "0")
     (set_tile "prt_23_cxi_02" "1")
    )
  )
)

;lê os dados iniciais da DCL no arquivo de dados
(defun prt_pt23_file ()
  (if (findfile (strcat cnp_root "/config/prt_pt23.txt"))
    (prt_pt23_readfile)
    (progn
      (setq file (open (strcat cnp_root "/config/prt_pt23.txt") "w" "utf8"))
      (write-line "1" file)
      (write-line "1" file)      
      (write-line "1" file)
      (write-line "1" file)
      (close file)
      (prt_pt23_readfile)
    )
  )
)


;função que lê o arquivo de dados
(defun prt_pt23_readfile ()
  (setq	file (open (strcat cnp_root "/config/prt_pt23.txt") "r" "utf8"))
  (setq	prt_pt23_soi (read-line file))
  (setq	prt_pt23_soe (read-line file))
  (setq	prt_pt23_ali (read-line file))
  (setq	prt_pt23_ale (read-line file))
  (close file)
)

;função que escreve o arquivo de dados
(defun prt_pt23_writefile ()
  (setq	file (open (strcat cnp_root "/config/prt_pt23.txt") "w" "utf8"))
  (write-line prt_pt23_soi file)
  (write-line prt_pt23_soe file)
  (write-line prt_pt23_ali file)
  (write-line prt_pt23_ale file)
  (close file)
)

;Desenha a porta
(defun prt_drw23 ()
  (cn7_init)
  (guarda '("blipmode" "cecolor" "celtype" "clayer" "cmdecho" "orthomode"
          "textstyle" "luprec" "osmode" ))
  (setvar "cecolor" "bylayer")
  (prt_pt23_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 1.0)
  (prt_drw23_caixilho)
  (prt_drw23_porta)
  (prt_drw23_soleira)
  (if (/= 0.0 prt_caix)
    (prt_drw23_alisar)
  )
  (prt_drw23_seta)
  (devolve)
  (prompt "\nUse o comando <UB> para retornar... ")
)

;*****************************************
;Desenho das Setas                        
;*****************************************
(defun prt_drw23_seta ()
  (cn7_verylayer "porta_seta" 1)
  (setq prt_seta (polar prt_porta1 prt_angbase (/ prt_larg 4.0))
	prt_seta (polar prt_seta (+ pi prt_angortho) (/ prt_wall 1.5))
  )
  (command "._insert" (strcat cnp_root "/blocos/prt_seta") "_s" (/ prt_blkscl 2.0) "_non" prt_seta (* 180 (/ prt_angbase pi)))
)


;*****************************************
;Desenho das Alisares                     
;*****************************************
(defun prt_drw23_alisar ()
  (cn7_verylayer prt_layc_all 7)
  (setvar "cecolor" prt_layc_alc)
  ;internos
  (if (= "1" prt_pt23_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._pline" "_non" prt_ali_a1 "_non" prt_ali_a2 "_non" prt_ali_a3 "_non" prt_ali_a4 "")
      (command "._pline" "_non" prt_ali_b1 "_non" prt_ali_b2 "_non" prt_ali_b3 "_non" prt_ali_b4 "")
    )
  )
  (if (= "1" prt_pt23_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._pline" "_non" prt_ale_a1 "_non" prt_ale_a2 "_non" prt_ale_a3 "_non" prt_ale_a4 "")
      (command "._pline" "_non" prt_ale_b1 "_non" prt_ale_b2 "_non" prt_ale_b3 "_non" prt_ale_b4 "")
    )
  )
)


;*****************************************
;Desenho das Soleiras                     
;*****************************************
(defun prt_drw23_soleira ()
  (cn7_verylayer prt_layc_sol 7)
  (setvar "cecolor" prt_layc_soc)
  (if (= prt_pt23_soi "1")
    (command "._pline" "_non" prt_cxi1 "_non" prt_cxi2 "")
  )
  (if (= prt_pt23_soe "1")
    (command "._pline" "_non" prt_cxi3 "_non" prt_cxi4 "")
  )
)

;*****************************************
;Desenho de Portas                        
;*****************************************
(defun prt_drw23_porta ()
  (setq prt_deltax (/ (- (/ prt_larg 2.0) (* prt_fator 5.0)) 7.0)
	prt_deltay (- prt_wall (/ prt_wall 4))
	prt_length (sqrt (+ (expt prt_deltax 2) (expt prt_deltay 2)))
	prt_angulo (atan (/ prt_deltay prt_deltax))
	prt_porta2 (polar prt_porta1 prt_angbase (* 5.0 prt_fator))
	prt_pti (polar prt_cxi1 prt_angortho (/ prt_wall 8.0))
	prt_pte (polar prt_cxi3 (+ prt_angortho pi) (/ prt_wall 8.0))
	prt_porta3 (polar prt_porta2 (+ prt_angbase prt_angulo) (/ prt_length 2.0))
	prt_porta4 (polar prt_porta3 (- prt_angbase prt_angulo) prt_length)
	prt_porta5 (polar prt_porta4 (+ prt_angbase prt_angulo) prt_length)
	prt_porta6 (polar prt_porta5 (- prt_angbase prt_angulo) prt_length)
	prt_porta7 (polar prt_porta6 (+ prt_angbase prt_angulo) prt_length)
	prt_porta8 (polar prt_porta7 (- prt_angbase prt_angulo) prt_length)
	prt_porta9 (polar prt_porta8 (+ prt_angbase prt_angulo) (/ prt_length 2.0))
	prt_porta10 (polar prt_porta9 prt_angbase (* 5.0 prt_fator))
  )
  (cn7_verylayer prt_layc_pol 7)
  (setvar "cecolor" prt_layc_poc)
  (command "._pline"  "_non" prt_porta1 "_non" prt_porta2  "_non" prt_porta3  "_non" prt_porta4  "_non" prt_porta5
	     "_non" prt_porta6  "_non" prt_porta7  "_non" prt_porta8  "_non" prt_porta9  "_non" prt_porta10 ""
  )
)

;*****************************************
;Desenho de Caixilho                      
;*****************************************

;desenha os caixihos
(defun prt_drw23_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
  (setq prt_porta1 (polar prt_cxi1 prt_angortho (/ prt_wall 2.0)))
)



;***********************************
;Porta Tipo 24                      
;Parte 01 - Configuração            
;***********************************
(defun prt_cfg_24 ()
  (prt_pt24_file)
  (setq dcl_id (load_dialog (strcat cnp_root "/lisp/cadnorma.dcl")))
  (if (not (new_dialog "prt_cfg_p24" dcl_id)) (exit))
  (set_tile "prt_descr" "Porta 'de Enrolar' (Lojas) ou Pivotante para Cima (Garagem)")
  ;slide de tipo
  (setq x (dimx_tile "prt_24_slide")
	y (dimy_tile "prt_24_slide")
  )
  (start_image "prt_24_slide")
  (fill_image 0 0 x y -2)
  (slide_image 0 0 x y (strcat cnp_root "/slides/prt_" prt_var_tipo ".sld"))
  (end_image)
  ;soleira
  (if (= "1" prt_pt24_soi) (set_tile "prt_24_solint"  "1"))
  (action_tile "prt_24_solint"  "(setq prt_pt24_soi $value)")
  (if (= "1" prt_pt24_soe) (set_tile "prt_24_solext"  "1"))
  (action_tile "prt_24_solext"  "(setq prt_pt24_soe $value)")
  ;tipo de porta
  (set_tile "prt_24_ptype" prt_pt24_typ)
  (action_tile "prt_24_ptype" "(setq prt_pt24_typ $value)")
  ;espessura da porta
  (set_tile "prt_24_poe_edit" prt_pt24_poe)
  (action_tile "prt_24_poe_edit" "(prt_24_poe_edit_act)")
  (action_tile "prt_24_poe_pick" "(done_dialog 2)")
  ;projeção
  (set_tile "prt_24_prjtog" prt_pt24_prj)
  (action_tile "prt_24_prjtog" "(setq prt_pt24_prj $value)")
  (set_tile "prt_24_prjwid" prt_pt24_wid)
  (action_tile "prt_24_prjwid" "(prt_24_wid_edit_act)")
  ;Desenhar fechaduras
  (set_tile "prt_24_fch_tog" prt_pt24_fch)
  (action_tile "prt_24_fch_tog" "(setq prt_pt24_fch $value)")
  ;Quantidade de portas
  (set_tile "prt_24_qtd_edit" prt_pt24_qtd)
  (action_tile "prt_24_qtd_edit" "(prt_24_qtd_edit_act)")
  (mode_tile "prt_24_qtd_edit" 2)
  ;ok_cancel
  (action_tile "cancel" "(done_dialog 0)")
  (action_tile "accept" "(done_dialog 1)")
  ;start_dialog
  (setq prt_24_id (start_dialog))
  (unload_dialog dcl_id)
  (if (= prt_24_id 1) (prt_pt24_writefile))
  (if (= prt_24_id 2) (prt_24_poe_button_act))
)



;lê os dados iniciais da DCL no arquivo de dados
(defun prt_pt24_file ()
  (if (findfile (strcat cnp_root "/config/prt_pt24.txt"))
    (prt_pt24_readfile)
    (progn
      (setq file (open (strcat cnp_root "/config/prt_pt24.txt") "w" "utf8"))
      (write-line "1" file)
      (write-line "1" file)      
      (write-line "prt_24_typ1" file)
      (write-line "3" file)
      (write-line "1" file)
      (write-line "40" file)
      (write-line "3" file)
      (write-line "1" file)
      (write-line "1" file)
      (close file)
      (prt_pt24_readfile)
    )
  )
)

;função que lê o arquivo de dados
(defun prt_pt24_readfile ()
  (setq	file (open (strcat cnp_root "/config/prt_pt24.txt") "r" "utf8"))
  (setq	prt_pt24_soi (read-line file))
  (setq	prt_pt24_soe (read-line file))
  (setq	prt_pt24_typ (read-line file))
  (setq	prt_pt24_poe (read-line file))
  (setq	prt_pt24_prj (read-line file))
  (setq	prt_pt24_wid (read-line file))
  (setq	prt_pt24_qtd (read-line file))
  (setq	prt_pt24_fch (read-line file))
  (close file)
)

;função que escreve o arquivo de dados
(defun prt_pt24_writefile ()
  (setq	file (open (strcat cnp_root "/config/prt_pt24.txt") "w" "utf8"))
  (write-line prt_pt24_soi file)
  (write-line prt_pt24_soe file)
  (write-line prt_pt24_typ file)
  (write-line prt_pt24_poe file)
  (write-line prt_pt24_prj file)
  (write-line prt_pt24_wid file)
  (write-line prt_pt24_qtd file)
  (write-line prt_pt24_fch file)
  (close file)
)

;Desenha a porta
(defun prt_drw24 ()
  (cn7_init)
  (guarda '("blipmode" "cecolor" "celtype" "clayer" "cmdecho" "orthomode"
          "textstyle" "luprec" "osmode" ))
  (setvar "cecolor" "bylayer")
  (prt_pt24_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_drw24_openfree 1.0)
  (prt_drw24_caixilho)
  (prt_drw24_soleira)
  (prt_drw24_batente)
  (prt_drw24_porta)
  (devolve)
  (prompt "\nUse o comando <UB> para retornar... ")
)


;desenha a fechadura
(defun prt_draw_fech ()
  (setq prt_fech0 (polar prt_porta1 prt_angbase (/ (distance prt_porta1 prt_porta3) 2.0))
	prt_fech1 (polar prt_fech0 (+ pi prt_angbase) (* prt_fator 5.0))
	prt_fech2 (polar prt_fech0 prt_angbase (* prt_fator 5.0))
	prt_fech3 (polar prt_fech2 prt_angortho (* prt_fator 3.0))
	prt_fech4 (polar prt_fech1 prt_angortho (* prt_fator 3.0))
  )
  (cn7_verylayer prt_layc_pol 7)
  (setvar "cecolor" prt_layc_poc)
  (command "._pline" "_non" prt_fech1  "_non" prt_fech2  "_non" prt_fech3  "_non" prt_fech4 "_c")
)

;denio

;desenha a projeção da porta
(defun prt_draw_proj ()
  (setq prt_proj1 (polar prt_porta2 (+ pi prt_angortho) (* prt_fator (distof prt_pt24_wid)))
	prt_proj2 (polar prt_porta4 (+ pi prt_angortho) (* prt_fator (distof prt_pt24_wid)))
  )
  (cn7_verylayer prt_layc_pol 7)
  (setvar "cecolor" "1")
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (command "._pline" "_non" prt_porta2 "_non" prt_proj1 "_non" prt_proj2 "_non" prt_porta4 "")
  (setvar "celtype" "bylayer")
)

;desenha a porta entre os batentes
(defun prt_draw24_porta ()
  (cn7_verylayer prt_layc_pol 7)
  (setvar "cecolor" prt_layc_poc)
  (setq prt_porta1 (polar prt_bat1 prt_angbase (* prt_fator 2.0))
	prt_porta1 (polar prt_porta1 prt_angortho (/ ( * prt_fator (distof prt_pt24_poe)) 2.0))
	prt_porta2 (polar prt_porta1 (+ pi prt_angortho) ( * prt_fator (distof prt_pt24_poe)))
	prt_porta3 (polar prt_bat2 (+ pi prt_angbase) (* prt_fator 2.0))
	prt_porta3 (polar prt_porta3 prt_angortho (/ ( * prt_fator (distof prt_pt24_poe)) 2.0))
	prt_porta4 (polar prt_porta3 (+ pi prt_angortho) ( * prt_fator (distof prt_pt24_poe)))
  )
  (command "._pline" "_non" prt_porta1 "_non" prt_porta2 "_non" prt_porta4 "_non" prt_porta3 "_c")
)

;desenha portas simples e mútiplas
(defun prt_drw24_porta ()
  (setq n_folhas (fix (distof prt_pt24_qtd)))
  (if (= n_folhas 1)
    (progn
      (prt_draw24_porta)
      (if (= "1" prt_pt24_fch) (prt_draw_fech))
      (if (= "1" prt_pt24_prj) (prt_draw_proj))
    )
    (progn
      (setq vao (/ prt_larg n_folhas)
	    prt_bat2 prt_bat1
      )
      (repeat (1- n_folhas)
	(setq prt_bat1 prt_bat2
	      prt_bat2  (polar prt_bat2 prt_angbase vao)
	      prt_bat1a (polar prt_bat1 (+ pi prt_angortho) (+ (/ ( * prt_fator (distof prt_pt24_poe)) 2.0) (* prt_fator 2)))
	      prt_bat1b (polar prt_bat1 prt_angortho (+ (/ ( * prt_fator (distof prt_pt24_poe)) 2.0) (* prt_fator 2)))
	      prt_bat1c (polar prt_bat1a prt_angbase ( * prt_fator (distof prt_pt24_poe)))
	      prt_bat1d (polar prt_bat1b prt_angbase ( * prt_fator (distof prt_pt24_poe)))
	      prt_bat2a (polar prt_bat2 (+ pi prt_angortho) (+ (/ ( * prt_fator (distof prt_pt24_poe)) 2.0) (* prt_fator 2)))
	      prt_bat2b (polar prt_bat2 prt_angortho (+ (/ ( * prt_fator (distof prt_pt24_poe)) 2.0) (* prt_fator 2)))
	      prt_bat2c (polar prt_bat2a (+ pi prt_angbase) ( * prt_fator (distof prt_pt24_poe)))
	      prt_bat2d (polar prt_bat2b (+ pi prt_angbase) ( * prt_fator (distof prt_pt24_poe)))
	      prt_bat2e (polar prt_bat2a prt_angbase ( * prt_fator (distof prt_pt24_poe)))
	      prt_bat2f (polar prt_bat2b prt_angbase ( * prt_fator (distof prt_pt24_poe)))
        )
	(cn7_verylayer "Porta_batentes" 2)
	(setvar "cecolor" "bylayer")
	(if (= prt_pt24_typ "prt_24_typ1")
	  (progn
	    (command "._pline" "_non" prt_bat2c "_non" prt_bat2e "")
	    (command "._pline" "_non" prt_bat2a "_non" prt_bat2b "")
	    (command "._pline" "_non" prt_bat2d "_non" prt_bat2f "")
          )
          (progn
	    (command "._pline" "_non" prt_bat2c "_non" prt_bat2e "")
	    (command "._pline" "_non" prt_bat2a "_non" prt_bat2b "")
          )
	)
	(prt_draw24_porta)
	(if (= "1" prt_pt24_fch) (prt_draw_fech))
	(if (= "1" prt_pt24_prj) (prt_draw_proj))
      );repeat
      (setq prt_bat1 prt_bat2
	    prt_bat2 (polar prt_bat2 prt_angbase vao)
	    prt_bat1a (polar prt_bat1 (+ pi prt_angortho) (+ (/ ( * prt_fator (distof prt_pt24_poe)) 2.0) (* prt_fator 2)))
	    prt_bat1b (polar prt_bat1 prt_angortho (+ (/ ( * prt_fator (distof prt_pt24_poe)) 2.0) (* prt_fator 2)))
	    prt_bat1c (polar prt_bat1a prt_angbase ( * prt_fator (distof prt_pt24_poe)))
	    prt_bat1d (polar prt_bat1b prt_angbase ( * prt_fator (distof prt_pt24_poe)))
	    prt_bat2a (polar prt_bat2 (+ pi prt_angortho) (+ (/ ( * prt_fator (distof prt_pt24_poe)) 2.0) (* prt_fator 2)))
	    prt_bat2b (polar prt_bat2 prt_angortho (+ (/ ( * prt_fator (distof prt_pt24_poe)) 2.0) (* prt_fator 2)))
	    prt_bat2c (polar prt_bat2a (+ pi prt_angbase) ( * prt_fator (distof prt_pt24_poe)))
	    prt_bat2d (polar prt_bat2b (+ pi prt_angbase) ( * prt_fator (distof prt_pt24_poe)))
      )
      (prt_draw24_porta)
      (if (= "1" prt_pt24_fch) (prt_draw_fech))
      (if (= "1" prt_pt24_prj) (prt_draw_proj))
     )	    
  )
)


;desenha os batentes para os dois tipos de portas
(defun prt_drw24_batente ()
  (setq prt_bat1 (polar prt_cxi1 prt_angortho (/ prt_wall 2.0))
	prt_bat2 (polar prt_cxi2 prt_angortho (/ prt_wall 2.0))
	prt_bat1a (polar prt_bat1 (+ pi prt_angortho) (+ (/ ( * prt_fator (distof prt_pt24_poe)) 2.0) (* prt_fator 2)))
	prt_bat1b (polar prt_bat1 prt_angortho (+ (/ ( * prt_fator (distof prt_pt24_poe)) 2.0) (* prt_fator 2)))
	prt_bat1c (polar prt_bat1a prt_angbase ( * prt_fator (distof prt_pt24_poe)))
	prt_bat1d (polar prt_bat1b prt_angbase ( * prt_fator (distof prt_pt24_poe)))
	prt_bat2a (polar prt_bat2 (+ pi prt_angortho) (+ (/ ( * prt_fator (distof prt_pt24_poe)) 2.0) (* prt_fator 2)))
	prt_bat2b (polar prt_bat2 prt_angortho (+ (/ ( * prt_fator (distof prt_pt24_poe)) 2.0) (* prt_fator 2)))
	prt_bat2c (polar prt_bat2a (+ pi prt_angbase) ( * prt_fator (distof prt_pt24_poe)))
	prt_bat2d (polar prt_bat2b (+ pi prt_angbase) ( * prt_fator (distof prt_pt24_poe)))
  )
  (cn7_verylayer "Porta_guias" 2)
  (setvar "cecolor" "bylayer")
  (if (= prt_pt24_typ "prt_24_typ1")
    (progn
      (command "._pline" "_non" prt_bat1c "_non" prt_bat1a "_non" prt_bat1b "_non" prt_bat1d "")
      (command "._pline" "_non" prt_bat2c "_non" prt_bat2a "_non" prt_bat2b "_non" prt_bat2d "")
    )
    (progn
      (command "._pline" "_non" prt_bat1c "_non" prt_bat1a "_non" prt_bat1b "")
      (command "._pline" "_non" prt_bat2c "_non" prt_bat2a "_non" prt_bat2b "")
    )
  )
)
    


;verifica se o valor de quantidade entrada é válida
(defun prt_24_qtd_edit_act ()
  (setq prt_var_newqtd $value)
  (if (and (distof prt_var_newqtd)
	   (equal (distof prt_var_newqtd) (fix (distof prt_var_newqtd)))
      )
    (progn
      (setq prt_pt24_qtd prt_var_newqtd)
      (prt_pt24_writefile)
    )
    (progn
      (alert "Valor Inválido!\nDigite um número inteiro.")
      (set_tile "prt_24_qtd_edit" prt_pt24_qtd)
      (mode_tile "prt_24_qtd_edit" 2)
    )
  )
)  

;verifica se o valor de largura entrada é válida
(defun prt_24_wid_edit_act ()
  (setq prt_var_newwid $value)
  (if (distof prt_var_newwid)
    (progn
      (setq prt_pt24_wid prt_var_newwid)
      (prt_pt24_writefile)
    )
    (progn
      (alert "Valor Inválido!")
      (set_tile "prt_24_wid_edit" prt_pt24_wid)
      (mode_tile "prt_24_wid_edit" 2)
    )
  )
)  


;Espessura por Pick Points
(defun prt_24_poe_button_act ()
  (prt_pt24_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt24_poe (rtos new_dist 2 2))
      (prt_pt24_writefile)
    )
  )
  (prt_cfg_24)
)


;verifica se o valor de espessura entrado é válido
(defun prt_24_poe_edit_act ()
  (setq prt_var_newpoe $value)
  (if (distof prt_var_newpoe)
    (progn
      (setq prt_pt24_poe prt_var_newpoe)
      (prt_pt24_writefile)
    )
    (progn
      (alert "Valor Inválido!")
      (set_tile "prt_24_poe_edit" prt_pt24_poe)
      (mode_tile "prt_24_poe_edit" 2)
    )
  )
)  


;*****************************************
;Desenho das Soleiras                     
;*****************************************
(defun prt_drw24_soleira ()
  (cn7_verylayer prt_layc_sol 7)
  (setvar "cecolor" prt_layc_soc)
  (if (= prt_pt24_soi "1")
    (command "._line" "_non" prt_cxi1 "_non" prt_cxi2 "")
  )
  (if (= prt_pt24_soe "1")
    (command "._line" "_non" prt_cxi3 "_non" prt_cxi4 "")
  )
)

;*****************************************
;Desenho de Caixilho                      
;*****************************************

;desenha os caixihos
(defun prt_drw24_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;*****************************************
;Abertura da parede                       
;*****************************************

;determina os pontos de 'break' das paredes
(defun prt_drw24_openfree (n)
  ;conversão de dados para numerais
  (prt_larg_file)
  (if (= prt_var_lrad "prt_larg_radio1")
    (setq prt_larg (* n (distof prt_pt24_qtd) prt_fator (distof (nth (fix (distof prt_var_larg)) prt_larg_list))))
    (setq prt_larg (* prt_fator (distof prt_var_lvao)))
  )
  (prt_halt_file)
  (setq prt_halt (* prt_fator (distof (nth (fix (distof prt_var_halt)) prt_halt_list)))
	prt_afas (* prt_fator (distof prt_var_afas))
	prt_wall (* prt_fator (distof prt_var_wall))
	prt_caix (* prt_fator (distof prt_var_caix))
  )
  ;clica na parede
  (prompt "\nSelecione a parede interna...")
  (setq prt_entsel (entsel)
	prt_ent1 (car prt_entsel)
	prt_ent1_type (cdr (assoc 0 (entget prt_ent1)))
	prt_pt0 (nth 0 (cdr prt_entsel))
	prt_ptt1 (cdr (assoc 10 (entget prt_ent1)))
	prt_ptt2 (cdr (assoc 11 (entget prt_ent1)))
	prt_wall_layer (cdr (assoc 8 (entget prt_ent1)))
  )
  (if (/= "LINE" prt_ent1_type)
    (progn
      (alert "A entidade Selecionada não é uma 'LINE'.\nPOLYLINES devem ser explodidas\npara usar este comando...")
      (prt_drw24_openfree 1.0)
    )
  )
  (if (<= (distance prt_pt0 prt_ptt1) (distance prt_pt0 prt_ptt2))
    (setq prt_pt1 prt_ptt1 prt_pt2 prt_ptt2 prt_code 1)
    (setq prt_pt1 prt_ptt2 prt_pt2 prt_ptt1 prt_code 2)
  )
  (setq prt_angbase (angle prt_pt1 prt_pt2))
  ;verifica o posicionamento para determinar os pontos de quebra
  (if (= prt_var_posi "prt_center")
    (setq prt_doll (/ (- (distance prt_pt1 prt_pt2) prt_larg (* 2 prt_caix)) 2))
    (setq prt_doll prt_afas)
  )
  (setq
	prt_brk1 (polar prt_pt1 prt_angbase prt_doll)
	prt_brk2 (polar prt_brk1 prt_angbase (+ prt_larg (* 2 prt_caix)))
  )
  (if (= prt_code 1)
    (setq prt_brk3a (polar prt_brk1 (- prt_angbase (/ pi 2)) prt_wall)
	  prt_brk3b (polar prt_brk1 (+ prt_angbase (/ pi 2)) prt_wall)
	  prt_brk4a (polar prt_brk2 (- prt_angbase (/ pi 2)) prt_wall)
	  prt_brk4b (polar prt_brk2 (+ prt_angbase (/ pi 2)) prt_wall)
    )
    (setq prt_brk3a (polar prt_brk1 (+ prt_angbase (/ pi 2)) prt_wall)
  	  prt_brk3b (polar prt_brk1 (- prt_angbase (/ pi 2)) prt_wall)
	  prt_brk4a (polar prt_brk2 (+ prt_angbase (/ pi 2)) prt_wall)
	  prt_brk4b (polar prt_brk2 (- prt_angbase (/ pi 2)) prt_wall)
    )
  )
  (if (/= nil (ssget "_f" (list prt_brk3a prt_brk4a) (list (cons 8 prt_wall_layer))))
    (progn
      (setq prt_brk3 prt_brk3a prt_brk4 prt_brk4a prt_xcode 1)
      (setq prt_brkm (polar prt_brk3 (angle prt_brk3 prt_brk4) (/ (distance prt_brk3 prt_brk4) 2)))
      (if (= nil (ssget "c" prt_brkm prt_brkm))
	(progn
	  (setq prt_brk3 prt_brk3b prt_brk4 prt_brk4b)
	  (setq prt_brkm (polar prt_brk3 (angle prt_brk3 prt_brk4) (/ (distance prt_brk3 prt_brk4) 2))
		prt_xcode 2)
	)
      )
    )
    (progn
      (setq prt_brk3 prt_brk3b prt_brk4 prt_brk4b prt_xcode 2)
      (setq prt_brkm (polar prt_brk3 (angle prt_brk3 prt_brk4) (/ (distance prt_brk3 prt_brk4) 2)))
      (if (= nil (ssget "c" prt_brkm prt_brkm))
	(progn
	  (setq prt_brk3 prt_brk3a prt_brk4 prt_brk4a)
	  (setq prt_brkm (polar prt_brk3 (angle prt_brk3 prt_brk4) (/ (distance prt_brk3 prt_brk4) 2))
		prt_xcode 4)
	)
      )
    )
  )
  (setq colmo (getvar "cecolor"))
  (command "._undo" "_m")
  (command "._break" prt_ent1 "_non" prt_brk1 "_non" prt_brk2)
  (command "._break" (ssget "c" prt_brkm prt_brkm) "_non" prt_brk3 "_non" prt_brk4)
  (command "._layer" "_s" prt_wall_layer "")
  (command "._line" "_non" prt_brk1 "_non" prt_brk3 "" "._line" "_non" prt_brk2 "_non" prt_brk4 "")
  (setq prt_angortho (angle prt_brk1 prt_brk3))
)



;***********************************
;Porta Tipo 31                      
;Parte 01 - Configuração            
;***********************************
(defun prt_cfg_31 ()
  (prt_pt31_file)
  (setq dcl_id (load_dialog (strcat cnp_root "/lisp/cadnorma.dcl")))
  (if (not (new_dialog "prt_cfg_p31" dcl_id)) (exit))
  (set_tile "prt_descr" "Porta de correr dupla, com uma folha fixa.")
  ;slide de tipo
  (setq x (dimx_tile "prt_31_slide")
	y (dimy_tile "prt_31_slide")
  )
  (start_image "prt_31_slide")
  (fill_image 0 0 x y -2)
  (slide_image 0 0 x y (strcat cnp_root "/slides/prt_" prt_var_tipo ".sld"))
  (end_image)
  ;espessura da porta
  (set_tile "prt_31_poe_edit" prt_pt31_poe)
  (action_tile "prt_31_poe_edit" "(prt_31_poe_edit_act)")
  (action_tile "prt_31_poe_pick" "(done_dialog 2)")
  ;soleira
  (if (= "1" prt_pt31_soi) (set_tile "prt_31_solint"  "1"))
  (action_tile "prt_31_solint"  "(setq prt_pt31_soi $value)")
  (if (= "1" prt_pt31_soe) (set_tile "prt_31_solext"  "1"))
  (action_tile "prt_31_solext"  "(setq prt_pt31_soe $value)")
  ;alisares
  (if (= "1" prt_pt31_ali) (set_tile "prt_31_aliint"  "1"))
  (action_tile "prt_31_aliint"  "(setq prt_pt31_ali $value)")
  (if (= "1" prt_pt31_ale) (set_tile "prt_31_aliext"  "1"))
  (action_tile "prt_31_aliext"  "(setq prt_pt31_ale $value)")
  ;ok_cancel
  (action_tile "cancel" "(done_dialog 0)")
  (action_tile "accept" "(done_dialog 1)")
  ;start_dialog
  (setq prt_31_id (start_dialog))
  (unload_dialog dcl_id)
  (if (= prt_31_id 1) (prt_pt31_writefile))
  (if (= prt_31_id 2) (prt_31_poe_button_act))
)

;Espessura por Pick Points
(defun prt_31_poe_button_act ()
  (prt_pt31_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt31_poe (rtos new_dist 2 2))
      (prt_pt31_writefile)
    )
  )
  (prt_cfg_31)
)

;verifica se o valor de espessura entrado é válido
(defun prt_31_poe_edit_act ()
  (setq prt_var_newpoe $value)
  (if (distof prt_var_newpoe)
    (progn
      (setq prt_pt31_poe prt_var_newpoe)
      (prt_pt31_writefile)
    )
    (progn
      (alert "Valor Inválido!")
      (set_tile "prt_31_poe_edit" prt_pt31_poe)
      (mode_tile "prt_31_poe_edit" 2)
    )
  )
)  


;lê os dados iniciais da DCL no arquivo de dados
(defun prt_pt31_file ()
  (if (findfile (strcat cnp_root "/config/prt_pt31.txt"))
    (prt_pt31_readfile)
    (progn
      (setq file (open (strcat cnp_root "/config/prt_pt31.txt") "w" "utf8"))
      (write-line "1" file)
      (write-line "1" file)      
      (write-line "1" file)
      (write-line "1" file)
      (write-line "3" file)
      (close file)
      (prt_pt31_readfile)
    )
  )
)

;função que lê o arquivo de dados
(defun prt_pt31_readfile ()
  (setq	file (open (strcat cnp_root "/config/prt_pt31.txt") "r" "utf8"))
  (setq	prt_pt31_soi (read-line file))
  (setq	prt_pt31_soe (read-line file))
  (setq	prt_pt31_ali (read-line file))
  (setq	prt_pt31_ale (read-line file))
  (setq	prt_pt31_poe (read-line file))
  (close file)
)

;função que escreve o arquivo de dados
(defun prt_pt31_writefile ()
  (setq	file (open (strcat cnp_root "/config/prt_pt31.txt") "w" "utf8"))
  (write-line prt_pt31_soi file)
  (write-line prt_pt31_soe file)
  (write-line prt_pt31_ali file)
  (write-line prt_pt31_ale file)
  (write-line prt_pt31_poe file)
  (close file)
)

;Desenha a porta
(defun prt_drw31 ()
  (cn7_init)
  (guarda '("blipmode" "cecolor" "celtype" "clayer" "cmdecho" "orthomode"
          "textstyle" "luprec" "osmode" ))
  (setvar "cecolor" "bylayer")
  (prt_pt31_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 2.0)
  (prt_drw31_caixilho)
  (prt_drw31_soleira)
  (if (/= 0.0 prt_caix)
    (prt_drw31_alisar)
  )
  (prt_drw31_porta)
  (prt_drw31_seta)
  (devolve)
  (prompt "\nUse o comando <UB> para retornar... ")
)

;*****************************************
;Desenho das Setas                        
;*****************************************
(defun prt_drw31_seta ()
  (cn7_verylayer "porta_seta" 1)
  (setq prt_seta (polar prt_porta4 prt_angbase (/ prt_larg 4.0))
	prt_seta (polar prt_seta (+ pi prt_angortho) (* prt_fator 7.5))
    )
  (command "._insert" (strcat cnp_root "/blocos/prt_seta") "_s" (/ prt_blkscl 1.25) "_non" prt_seta (* 180 (/ prt_angbase pi)))
)

;*****************************************
;Desenho das Portas                       
;*****************************************
(defun prt_drw31_porta ()
  (setq prt_porta0 (polar prt_cxi1 prt_angortho (/ prt_wall 2.0))
	prt_porta1 (polar prt_porta0 prt_angbase (/ prt_larg 4.0))
	prt_porta2 (polar prt_porta1 prt_angbase (/ prt_larg 2.0))
	prt_porta3 (polar prt_porta2 (+ pi prt_angortho) (* prt_fator (distof prt_pt31_poe)))
	prt_porta4 (polar prt_porta3 (+ pi prt_angbase) (/ prt_larg 2.0))
	prt_porta5 (polar prt_porta1 prt_angbase (/ prt_larg 4.0))
	prt_porta6 (polar prt_porta5 prt_angbase (/ prt_larg 2.0))
	prt_porta7 (polar prt_porta6 prt_angortho (* prt_fator (distof prt_pt31_poe)))
	prt_porta8 (polar prt_porta7 (+ pi prt_angbase) (/ prt_larg 2.0))
  )
  (command "._pline" "_non" prt_porta1 "_non" prt_porta2  "_non" prt_porta3  "_non" prt_porta4 "_c"
	   "._pline" "_non" prt_porta5 "_non" prt_porta6  "_non" prt_porta7  "_non" prt_porta8 "_c"
  )
)

;*****************************************
;Desenho das Alisares                     
;*****************************************
(defun prt_drw31_alisar ()
  (cn7_verylayer prt_layc_all 7)
  (setvar "cecolor" prt_layc_alc)
  ;internos
  (if (= "1" prt_pt31_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt31_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw31_soleira ()
  (cn7_verylayer prt_layc_sol 7)
  (setvar "cecolor" prt_layc_soc)
  (if (= prt_pt31_soi "1")
    (command "._line" "_non" prt_cxi1 "_non" prt_cxi2 "")
  )
  (if (= prt_pt31_soe "1")
    (command "._line" "_non" prt_cxi3 "_non" prt_cxi4 "")
  )
)

;*****************************************
;Desenho de Caixilho                      
;*****************************************

;desenha os caixihos
(defun prt_drw31_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 32                      
;Parte 01 - Configuração            
;***********************************
(defun prt_cfg_32 ()
  (prt_pt32_file)
  (setq dcl_id (load_dialog (strcat cnp_root "/lisp/cadnorma.dcl")))
  (if (not (new_dialog "prt_cfg_p32" dcl_id)) (exit))
  (set_tile "prt_descr" "Porta de correr tripla, com duas bandeiras fixas.")
  ;slide de tipo
  (setq x (dimx_tile "prt_32_slide")
	y (dimy_tile "prt_32_slide")
  )
  (start_image "prt_32_slide")
  (fill_image 0 0 x y -2)
  (slide_image 0 0 x y (strcat cnp_root "/slides/prt_" prt_var_tipo ".sld"))
  (end_image)
  ;espessura da porta
  (set_tile "prt_32_poe_edit" prt_pt32_poe)
  (action_tile "prt_32_poe_edit" "(prt_32_poe_edit_act)")
  (action_tile "prt_32_poe_pick" "(done_dialog 2)")
  ;soleira
  (if (= "1" prt_pt32_soi) (set_tile "prt_32_solint"  "1"))
  (action_tile "prt_32_solint"  "(setq prt_pt32_soi $value)")
  (if (= "1" prt_pt32_soe) (set_tile "prt_32_solext"  "1"))
  (action_tile "prt_32_solext"  "(setq prt_pt32_soe $value)")
  ;alisares
  (if (= "1" prt_pt32_ali) (set_tile "prt_32_aliint"  "1"))
  (action_tile "prt_32_aliint"  "(setq prt_pt32_ali $value)")
  (if (= "1" prt_pt32_ale) (set_tile "prt_32_aliext"  "1"))
  (action_tile "prt_32_aliext"  "(setq prt_pt32_ale $value)")
  ;ok_cancel
  (action_tile "cancel" "(done_dialog 0)")
  (action_tile "accept" "(done_dialog 1)")
  ;start_dialog
  (setq prt_32_id (start_dialog))
  (unload_dialog dcl_id)
  (if (= prt_32_id 1) (prt_pt32_writefile))
  (if (= prt_32_id 2) (prt_32_poe_button_act))
)

;Espessura por Pick Points
(defun prt_32_poe_button_act ()
  (prt_pt32_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt32_poe (rtos new_dist 2 2))
      (prt_pt32_writefile)
    )
  )
  (prt_cfg_32)
)

;verifica se o valor de espessura entrado é válido
(defun prt_32_poe_edit_act ()
  (setq prt_var_newpoe $value)
  (if (distof prt_var_newpoe)
    (progn
      (setq prt_pt32_poe prt_var_newpoe)
      (prt_pt32_writefile)
    )
    (progn
      (alert "Valor Inválido!")
      (set_tile "prt_32_poe_edit" prt_pt32_poe)
      (mode_tile "prt_32_poe_edit" 2)
    )
  )
)  


;lê os dados iniciais da DCL no arquivo de dados
(defun prt_pt32_file ()
  (if (findfile (strcat cnp_root "/config/prt_pt32.txt"))
    (prt_pt32_readfile)
    (progn
      (setq file (open (strcat cnp_root "/config/prt_pt32.txt") "w" "utf8"))
      (write-line "1" file)
      (write-line "1" file)      
      (write-line "1" file)
      (write-line "1" file)
      (write-line "3" file)
      (close file)
      (prt_pt32_readfile)
    )
  )
)

;função que lê o arquivo de dados
(defun prt_pt32_readfile ()
  (setq	file (open (strcat cnp_root "/config/prt_pt32.txt") "r" "utf8"))
  (setq	prt_pt32_soi (read-line file))
  (setq	prt_pt32_soe (read-line file))
  (setq	prt_pt32_ali (read-line file))
  (setq	prt_pt32_ale (read-line file))
  (setq	prt_pt32_poe (read-line file))
  (close file)
)

;função que escreve o arquivo de dados
(defun prt_pt32_writefile ()
  (setq	file (open (strcat cnp_root "/config/prt_pt32.txt") "w" "utf8"))
  (write-line prt_pt32_soi file)
  (write-line prt_pt32_soe file)
  (write-line prt_pt32_ali file)
  (write-line prt_pt32_ale file)
  (write-line prt_pt32_poe file)
  (close file)
)

;Desenha a porta
(defun prt_drw32 ()
  (cn7_init)
  (guarda '("blipmode" "cecolor" "celtype" "clayer" "cmdecho" "orthomode"
          "textstyle" "luprec" "osmode" ))
  (setvar "cecolor" "bylayer")
  (prt_pt32_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 3.0)
  (prt_drw32_caixilho)
  (prt_drw32_soleira)
  (if (/= 0.0 prt_caix)
    (prt_drw32_alisar)
  )
  (prt_drw32_porta)
  (prt_drw32_seta)
  (devolve)
  (prompt "\nUse o comando <UB> para retornar... ")
)

;*****************************************
;Desenho das Setas                        
;*****************************************
(defun prt_drw32_seta ()
  (cn7_verylayer "porta_seta" 1)
  (setq prt_seta (polar prt_porta4 prt_angbase (/ prt_larg 6.0))
	prt_seta (polar prt_seta (+ pi prt_angortho) (* prt_fator 7.5))
    )
  (command "._insert" (strcat cnp_root "/blocos/prt_seta") "_s" (/ prt_blkscl 1.25) "_non" prt_seta (* 180 (/ prt_angbase pi)))
)

;*****************************************
;Desenho das Portas                       
;*****************************************
(defun prt_drw32_porta ()
  (setq prt_porta0 (polar prt_cxi1 prt_angortho (/ prt_wall 2.0))
	prt_porta1 (polar prt_porta0 prt_angbase (/ prt_larg 2.0))
	prt_porta2 (polar prt_porta1 prt_angbase (/ prt_larg 3.0))
	prt_porta3 (polar prt_porta2 (+ pi prt_angortho) (* prt_fator (distof prt_pt32_poe)))
	prt_porta4 (polar prt_porta3 (+ pi prt_angbase) (/ prt_larg 3.0))
	prt_porta5 (polar prt_porta1 prt_angbase (/ prt_larg 6.0))
	prt_porta6 (polar prt_porta5 prt_angbase (/ prt_larg 3.0))
	prt_porta7 (polar prt_porta6 prt_angortho (* prt_fator (distof prt_pt32_poe)))
	prt_porta8 (polar prt_porta7 (+ pi prt_angbase) (/ prt_larg 3.0))
	prt_porta9 (polar prt_porta0 prt_angbase (/ prt_larg 3.0))
	prt_porta10 (polar prt_porta9 (+ pi prt_angortho) (* prt_fator (distof prt_pt32_poe)))
	prt_porta11 (polar prt_porta10 (+ pi prt_angbase) (/ prt_larg 3.0))
  )
  (command "._pline" "_non" prt_porta1 "_non" prt_porta2  "_non" prt_porta3  "_non" prt_porta4 "_c"
	   "._pline" "_non" prt_porta5 "_non" prt_porta6  "_non" prt_porta7  "_non" prt_porta8 "_c"
	   "._pline" "_non" prt_porta0 "_non" prt_porta9  "_non" prt_porta10  "_non" prt_porta11 "_c"
  )
)

;*****************************************
;Desenho das Alisares                     
;*****************************************
(defun prt_drw32_alisar ()
  (cn7_verylayer prt_layc_all 7)
  (setvar "cecolor" prt_layc_alc)
  ;internos
  (if (= "1" prt_pt32_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt32_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw32_soleira ()
  (cn7_verylayer prt_layc_sol 7)
  (setvar "cecolor" prt_layc_soc)
  (if (= prt_pt32_soi "1")
    (command "._line" "_non" prt_cxi1 "_non" prt_cxi2 "")
  )
  (if (= prt_pt32_soe "1")
    (command "._line" "_non" prt_cxi3 "_non" prt_cxi4 "")
  )
)

;*****************************************
;Desenho de Caixilho                      
;*****************************************

;desenha os caixihos
(defun prt_drw32_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 33                      
;Parte 01 - Configuração            
;***********************************
(defun prt_cfg_33 ()
  (prt_pt33_file)
  (setq dcl_id (load_dialog (strcat cnp_root "/lisp/cadnorma.dcl")))
  (if (not (new_dialog "prt_cfg_p33" dcl_id)) (exit))
  (set_tile "prt_descr" "Porta de correr quádrupla, duas bandeiras fixas.")
  ;slide de tipo
  (setq x (dimx_tile "prt_33_slide")
	y (dimy_tile "prt_33_slide")
  )
  (start_image "prt_33_slide")
  (fill_image 0 0 x y -2)
  (slide_image 0 0 x y (strcat cnp_root "/slides/prt_" prt_var_tipo ".sld"))
  (end_image)
  ;espessura da porta
  (set_tile "prt_33_poe_edit" prt_pt33_poe)
  (action_tile "prt_33_poe_edit" "(prt_33_poe_edit_act)")
  (action_tile "prt_33_poe_pick" "(done_dialog 2)")
  ;soleira
  (if (= "1" prt_pt33_soi) (set_tile "prt_33_solint"  "1"))
  (action_tile "prt_33_solint"  "(setq prt_pt33_soi $value)")
  (if (= "1" prt_pt33_soe) (set_tile "prt_33_solext"  "1"))
  (action_tile "prt_33_solext"  "(setq prt_pt33_soe $value)")
  ;alisares
  (if (= "1" prt_pt33_ali) (set_tile "prt_33_aliint"  "1"))
  (action_tile "prt_33_aliint"  "(setq prt_pt33_ali $value)")
  (if (= "1" prt_pt33_ale) (set_tile "prt_33_aliext"  "1"))
  (action_tile "prt_33_aliext"  "(setq prt_pt33_ale $value)")
  ;ok_cancel
  (action_tile "cancel" "(done_dialog 0)")
  (action_tile "accept" "(done_dialog 1)")
  ;start_dialog
  (setq prt_33_id (start_dialog))
  (unload_dialog dcl_id)
  (if (= prt_33_id 1) (prt_pt33_writefile))
  (if (= prt_33_id 2) (prt_33_poe_button_act))
)

;Espessura por Pick Points
(defun prt_33_poe_button_act ()
  (prt_pt33_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt33_poe (rtos new_dist 2 2))
      (prt_pt33_writefile)
    )
  )
  (prt_cfg_33)
)

;verifica se o valor de espessura entrado é válido
(defun prt_33_poe_edit_act ()
  (setq prt_var_newpoe $value)
  (if (distof prt_var_newpoe)
    (progn
      (setq prt_pt33_poe prt_var_newpoe)
      (prt_pt33_writefile)
    )
    (progn
      (alert "Valor Inválido!")
      (set_tile "prt_33_poe_edit" prt_pt33_poe)
      (mode_tile "prt_33_poe_edit" 2)
    )
  )
)  


;lê os dados iniciais da DCL no arquivo de dados
(defun prt_pt33_file ()
  (if (findfile (strcat cnp_root "/config/prt_pt33.txt"))
    (prt_pt33_readfile)
    (progn
      (setq file (open (strcat cnp_root "/config/prt_pt33.txt") "w" "utf8"))
      (write-line "1" file)
      (write-line "1" file)      
      (write-line "1" file)
      (write-line "1" file)
      (write-line "3" file)
      (close file)
      (prt_pt33_readfile)
    )
  )
)

;função que lê o arquivo de dados
(defun prt_pt33_readfile ()
  (setq	file (open (strcat cnp_root "/config/prt_pt33.txt") "r" "utf8"))
  (setq	prt_pt33_soi (read-line file))
  (setq	prt_pt33_soe (read-line file))
  (setq	prt_pt33_ali (read-line file))
  (setq	prt_pt33_ale (read-line file))
  (setq	prt_pt33_poe (read-line file))
  (close file)
)

;função que escreve o arquivo de dados
(defun prt_pt33_writefile ()
  (setq	file (open (strcat cnp_root "/config/prt_pt33.txt") "w" "utf8"))
  (write-line prt_pt33_soi file)
  (write-line prt_pt33_soe file)
  (write-line prt_pt33_ali file)
  (write-line prt_pt33_ale file)
  (write-line prt_pt33_poe file)
  (close file)
)

;Desenha a porta
(defun prt_drw33 ()
  (cn7_init)
  (guarda '("blipmode" "cecolor" "celtype" "clayer" "cmdecho" "orthomode"
          "textstyle" "luprec" "osmode" ))
  (setvar "cecolor" "bylayer")
  (prt_pt33_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 4.0)
  (prt_drw33_caixilho)
  (prt_drw33_soleira)
  (if (/= 0.0 prt_caix)
    (prt_drw33_alisar)
  )
  (prt_drw33_porta)
  (prt_drw33_seta)
  (devolve)
  (prompt "\nUse o comando <UB> para retornar... ")
)

;*****************************************
;Desenho das Setas                        
;*****************************************
(defun prt_drw33_seta ()
  (cn7_verylayer "porta_seta" 1)
  (setq prt_seta (polar prt_porta15 prt_angbase (/ prt_larg 8.0))
	prt_seta (polar prt_seta (+ pi prt_angortho) (* prt_fator 7.5))
    )
  (command "._insert" (strcat cnp_root "/blocos/prt_seta") "_s" (/ prt_blkscl 1.25) "_non" prt_seta (* 180 (/ prt_angbase pi)))
  (setq prt_seta (polar prt_seta prt_angbase (/ prt_larg 2.0)))
  (command "._insert" (strcat cnp_root "/blocos/prt_seta") "_s" (/ prt_blkscl 1.25) "_non" prt_seta (* 180 (/ prt_angbase pi)))
)

;*****************************************
;Desenho das Portas                       
;*****************************************
(defun prt_drw33_porta ()
  (setq prt_porta0 (polar prt_cxi1 prt_angortho (/ prt_wall 2.0))
	prt_porta1 (polar prt_porta0 prt_angbase (* 5 (/ prt_larg 8.0)))
	prt_porta2 (polar prt_porta1 prt_angbase (/ prt_larg 4.0))
	prt_porta3 (polar prt_porta2 (+ pi prt_angortho) (* prt_fator (distof prt_pt33_poe)))
	prt_porta4 (polar prt_porta3 (+ pi prt_angbase) (/ prt_larg 4.0))
	prt_porta5 (polar prt_porta1 prt_angbase (/ prt_larg 8.0))
	prt_porta6 (polar prt_porta5 prt_angbase (/ prt_larg 4.0))
	prt_porta7 (polar prt_porta6 prt_angortho (* prt_fator (distof prt_pt33_poe)))
	prt_porta8 (polar prt_porta7 (+ pi prt_angbase) (/ prt_larg 4.0))
	prt_porta9 (polar prt_porta0 prt_angbase (/ prt_larg 4.0))
	prt_porta10 (polar prt_porta9 prt_angortho (* prt_fator (distof prt_pt33_poe)))
	prt_porta11 (polar prt_porta10 (+ pi prt_angbase) (/ prt_larg 4.0))
	prt_porta12 (polar prt_porta0 prt_angbase (/ prt_larg 8.0))
	prt_porta13 (polar prt_porta12 prt_angbase (/ prt_larg 4.0))
	prt_porta14 (polar prt_porta13 (+ pi prt_angortho) (* prt_fator (distof prt_pt33_poe)))
	prt_porta15 (polar prt_porta14 (+ pi prt_angbase) (/ prt_larg 4.0))
  )
  (command "._pline" "_non" prt_porta1 "_non" prt_porta2  "_non" prt_porta3  "_non" prt_porta4 "_c"
	   "._pline" "_non" prt_porta5 "_non" prt_porta6  "_non" prt_porta7  "_non" prt_porta8 "_c"
	   "._pline" "_non" prt_porta0 "_non" prt_porta9  "_non" prt_porta10  "_non" prt_porta11 "_c"
	   "._pline" "_non" prt_porta12 "_non" prt_porta13  "_non" prt_porta14  "_non" prt_porta15 "_c"
  )
)

;*****************************************
;Desenho das Alisares                     
;*****************************************
(defun prt_drw33_alisar ()
  (cn7_verylayer prt_layc_all 7)
  (setvar "cecolor" prt_layc_alc)
  ;internos
  (if (= "1" prt_pt33_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt33_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw33_soleira ()
  (cn7_verylayer prt_layc_sol 7)
  (setvar "cecolor" prt_layc_soc)
  (if (= prt_pt33_soi "1")
    (command "._line" "_non" prt_cxi1 "_non" prt_cxi2 "")
  )
  (if (= prt_pt33_soe "1")
    (command "._line" "_non" prt_cxi3 "_non" prt_cxi4 "")
  )
)

;*****************************************
;Desenho de Caixilho                      
;*****************************************

;desenha os caixihos
(defun prt_drw33_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 34                      
;Parte 01 - Configuração            
;***********************************
(defun prt_cfg_34 ()
  (prt_pt34_file)
  (setq dcl_id (load_dialog (strcat cnp_root "/lisp/cadnorma.dcl")))
  (if (not (new_dialog "prt_cfg_p34" dcl_id)) (exit))
  (set_tile "prt_descr" "Porta de correr quádrupla, duas bandeiras fixas.")
  ;slide de tipo
  (setq x (dimx_tile "prt_34_slide")
	y (dimy_tile "prt_34_slide")
  )
  (start_image "prt_34_slide")
  (fill_image 0 0 x y -2)
  (slide_image 0 0 x y (strcat cnp_root "/slides/prt_" prt_var_tipo ".sld"))
  (end_image)
  ;espessura da porta
  (set_tile "prt_34_poe_edit" prt_pt34_poe)
  (action_tile "prt_34_poe_edit" "(prt_34_poe_edit_act)")
  (action_tile "prt_34_poe_pick" "(done_dialog 2)")
  ;soleira
  (if (= "1" prt_pt34_soi) (set_tile "prt_34_solint"  "1"))
  (action_tile "prt_34_solint"  "(setq prt_pt34_soi $value)")
  (if (= "1" prt_pt34_soe) (set_tile "prt_34_solext"  "1"))
  (action_tile "prt_34_solext"  "(setq prt_pt34_soe $value)")
  ;alisares
  (if (= "1" prt_pt34_ali) (set_tile "prt_34_aliint"  "1"))
  (action_tile "prt_34_aliint"  "(setq prt_pt34_ali $value)")
  (if (= "1" prt_pt34_ale) (set_tile "prt_34_aliext"  "1"))
  (action_tile "prt_34_aliext"  "(setq prt_pt34_ale $value)")
  ;quantidade de portas
  (set_tile "prt_34_qtd_edit" prt_pt34_qtd)
  (action_tile "prt_34_qtd_edit" "(prt_34_qtd_edit_act)")
  (mode_tile "prt_34_qtd_edit" 2)
  ;ok_cancel
  (action_tile "cancel" "(done_dialog 0)")
  (action_tile "accept" "(done_dialog 1)")
  ;start_dialog
  (setq prt_34_id (start_dialog))
  (unload_dialog dcl_id)
  (if (= prt_34_id 1) (prt_pt34_writefile))
  (if (= prt_34_id 2) (prt_34_poe_button_act))
)


;verifica se o valor de quantidade entrada é válida
(defun prt_34_qtd_edit_act ()
  (setq prt_var_newqtd $value)
  (if (and (distof prt_var_newqtd)
	   (equal (distof prt_var_newqtd) (fix (distof prt_var_newqtd)))
      )
    (progn
      (setq prt_pt34_qtd prt_var_newqtd)
      (prt_pt34_writefile)
    )
    (progn
      (alert "Valor Inválido!\nDigite um número inteiro.")
      (set_tile "prt_34_qtd_edit" prt_pt34_qtd)
      (mode_tile "prt_34_qtd_edit" 2)
    )
  )
)  

;Espessura por Pick Points
(defun prt_34_poe_button_act ()
  (prt_pt34_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt34_poe (rtos new_dist 2 2))
      (prt_pt34_writefile)
    )
  )
  (prt_cfg_34)
)

;verifica se o valor de espessura entrado é válido
(defun prt_34_poe_edit_act ()
  (setq prt_var_newpoe $value)
  (if (distof prt_var_newpoe)
    (progn
      (setq prt_pt34_poe prt_var_newpoe)
      (prt_pt34_writefile)
    )
    (progn
      (alert "Valor Inválido!")
      (set_tile "prt_34_poe_edit" prt_pt34_poe)
      (mode_tile "prt_34_poe_edit" 2)
    )
  )
)  


;lê os dados iniciais da DCL no arquivo de dados
(defun prt_pt34_file ()
  (if (findfile (strcat cnp_root "/config/prt_pt34.txt"))
    (prt_pt34_readfile)
    (progn
      (setq file (open (strcat cnp_root "/config/prt_pt34.txt") "w" "utf8"))
      (write-line "1" file)
      (write-line "1" file)      
      (write-line "1" file)
      (write-line "1" file)
      (write-line "3" file)
      (write-line "1" file)
      (close file)
      (prt_pt34_readfile)
    )
  )
)

;função que lê o arquivo de dados
(defun prt_pt34_readfile ()
  (setq	file (open (strcat cnp_root "/config/prt_pt34.txt") "r" "utf8"))
  (setq	prt_pt34_soi (read-line file))
  (setq	prt_pt34_soe (read-line file))
  (setq	prt_pt34_ali (read-line file))
  (setq	prt_pt34_ale (read-line file))
  (setq	prt_pt34_poe (read-line file))
  (setq	prt_pt34_qtd (read-line file))
  (close file)
)

;função que escreve o arquivo de dados
(defun prt_pt34_writefile ()
  (setq	file (open (strcat cnp_root "/config/prt_pt34.txt") "w" "utf8"))
  (write-line prt_pt34_soi file)
  (write-line prt_pt34_soe file)
  (write-line prt_pt34_ali file)
  (write-line prt_pt34_ale file)
  (write-line prt_pt34_poe file)
  (write-line prt_pt34_qtd file)
  (close file)
)

;Desenha a porta
(defun prt_drw34 ()
  (cn7_init)
  (guarda '("blipmode" "cecolor" "celtype" "clayer" "cmdecho" "orthomode"
          "textstyle" "luprec" "osmode" ))
  (setvar "cecolor" "bylayer")
  (prt_pt34_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_drw34_openfree 1.0)
  (prt_drw34_caixilho)
  (prt_drw34_soleira)
  (if (/= 0.0 prt_caix)
    (prt_drw34_alisar)
  )
  (prt_drw34_porta)
  (devolve)
  (prompt "\nUse o comando <UB> para retornar... ")
)

;desenha a porta entre os batentes
(defun prt_draw34_porta ()
  (cn7_verylayer prt_layc_pol 7)
  (setvar "cecolor" prt_layc_poc)
  (setq prt_porta0 (polar prt_bat1 prt_angbase (/ (/ prt_larg n_folhas) 2.0))
	prt_porta0a (polar prt_porta0 (+ prt_angbase (/ (* 3 pi) 4)) (/ (/ prt_larg n_folhas) 2.0))
	prt_porta0b (polar prt_porta0 (- prt_angbase (/ pi 4)) (/ (/ prt_larg n_folhas) 2.0))
	prt_porta1 (polar prt_porta0a (+ prt_angbase (* 5 (/ pi 4))) (/ (* prt_fator (distof prt_pt34_poe)) 2))
	prt_porta2 (polar prt_porta0a (+ prt_angbase (/ pi 4)) (/ (* prt_fator (distof prt_pt34_poe)) 2))
	prt_porta3 (polar prt_porta0b (+ prt_angbase (* 5 (/ pi 4))) (/ (* prt_fator (distof prt_pt34_poe)) 2))
	prt_porta4 (polar prt_porta0b (+ prt_angbase (/ pi 4)) (/ (* prt_fator (distof prt_pt34_poe)) 2))
  )
  (command "._pline" "_non" prt_porta1 "_non" prt_porta2   "_non" prt_porta4  "_non" prt_porta3 "_c"
	   "._donut" 0.0 (/ (* prt_fator (distof prt_pt34_poe)) 2) "_non" prt_porta0 ""
  )
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (setvar "celtype" "hidden2")
  (cn7_verylayer prt_layc_arl 7)
  (setvar "cecolor" prt_layc_arc)
  (command "._arc" "_non" prt_porta1 "_e" "_non" prt_bat1 "_a" "45"
	   "._arc" "_non" prt_porta4 "_e" "_non" prt_bat2 "_a" "45"
  )
  (setvar "celtype" "bylayer")
)


;*****************************************
;Desenho das Portas                       
;*****************************************
(defun prt_drw34_porta ()
  (setq n_folhas (fix (distof prt_pt34_qtd)))
  (if (= n_folhas 1)
    (progn
      (setq prt_bat1 (polar prt_cxi1 prt_angortho (/ prt_wall 2.0))
	    prt_bat2 (polar prt_cxi2 prt_angortho (/ prt_wall 2.0))
      )
      (prt_draw34_porta)
    )
    (progn
      (setq vao (/ prt_larg n_folhas)
	    prt_bat1 (polar prt_cxi1 prt_angortho (/ prt_wall 2.0))
	    prt_bat2 prt_bat1
      )
      (repeat (1- n_folhas)
	(setq prt_bat1 prt_bat2
	      prt_bat2  (polar prt_bat2 prt_angbase vao)
        )
	(prt_draw34_porta)
      );repeat
      (setq prt_bat1 prt_bat2
	    prt_bat2 (polar prt_bat2 prt_angbase vao)
      )
      (prt_draw34_porta)
     )	    
  )
)

;*****************************************
;Desenho das Alisares                     
;*****************************************
(defun prt_drw34_alisar ()
  (cn7_verylayer prt_layc_all 7)
  (setvar "cecolor" prt_layc_alc)
  ;internos
  (if (= "1" prt_pt34_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt34_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw34_soleira ()
  (cn7_verylayer prt_layc_sol 7)
  (setvar "cecolor" prt_layc_soc)
  (if (= prt_pt34_soi "1")
    (command "._line" "_non" prt_cxi1 "_non" prt_cxi2 "")
  )
  (if (= prt_pt34_soe "1")
    (command "._line" "_non" prt_cxi3 "_non" prt_cxi4 "")
  )
)

;*****************************************
;Desenho de Caixilho                      
;*****************************************

;desenha os caixihos
(defun prt_drw34_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)


;*****************************************
;Abertura da parede                       
;*****************************************

;determina os pontos de 'break' das paredes
(defun prt_drw34_openfree (n)
  ;conversão de dados para numerais
  (prt_larg_file)
  (if (= prt_var_lrad "prt_larg_radio1")
    (setq prt_larg (* n (distof prt_pt34_qtd) prt_fator (distof (nth (fix (distof prt_var_larg)) prt_larg_list))))
    (setq prt_larg (* prt_fator (distof prt_var_lvao)))
  )
  (prt_halt_file)
  (setq prt_halt (* prt_fator (distof (nth (fix (distof prt_var_halt)) prt_halt_list)))
	prt_afas (* prt_fator (distof prt_var_afas))
	prt_wall (* prt_fator (distof prt_var_wall))
	prt_caix (* prt_fator (distof prt_var_caix))
  )
  ;clica na parede
  (prompt "\nSelecione a parede interna...")
  (setq prt_entsel (entsel)
	prt_ent1 (car prt_entsel)
	prt_ent1_type (cdr (assoc 0 (entget prt_ent1)))
	prt_pt0 (nth 0 (cdr prt_entsel))
	prt_ptt1 (cdr (assoc 10 (entget prt_ent1)))
	prt_ptt2 (cdr (assoc 11 (entget prt_ent1)))
	prt_wall_layer (cdr (assoc 8 (entget prt_ent1)))
  )
  (if (/= "LINE" prt_ent1_type)
    (progn
      (alert "A entidade Selecionada não é uma 'LINE'.\nPOLYLINES devem ser explodidas\npara usar este comando...")
      (prt_drw34_openfree 1.0)
    )
  )
  (if (<= (distance prt_pt0 prt_ptt1) (distance prt_pt0 prt_ptt2))
    (setq prt_pt1 prt_ptt1 prt_pt2 prt_ptt2 prt_code 1)
    (setq prt_pt1 prt_ptt2 prt_pt2 prt_ptt1 prt_code 2)
  )
  (setq prt_angbase (angle prt_pt1 prt_pt2))
  ;verifica o posicionamento para determinar os pontos de quebra
  (if (= prt_var_posi "prt_center")
    (setq prt_doll (/ (- (distance prt_pt1 prt_pt2) prt_larg (* 2 prt_caix)) 2))
    (setq prt_doll prt_afas)
  )
  (setq
	prt_brk1 (polar prt_pt1 prt_angbase prt_doll)
	prt_brk2 (polar prt_brk1 prt_angbase (+ prt_larg (* 2 prt_caix)))
  )
  (if (= prt_code 1)
    (setq prt_brk3a (polar prt_brk1 (- prt_angbase (/ pi 2)) prt_wall)
	  prt_brk3b (polar prt_brk1 (+ prt_angbase (/ pi 2)) prt_wall)
	  prt_brk4a (polar prt_brk2 (- prt_angbase (/ pi 2)) prt_wall)
	  prt_brk4b (polar prt_brk2 (+ prt_angbase (/ pi 2)) prt_wall)
    )
    (setq prt_brk3a (polar prt_brk1 (+ prt_angbase (/ pi 2)) prt_wall)
  	  prt_brk3b (polar prt_brk1 (- prt_angbase (/ pi 2)) prt_wall)
	  prt_brk4a (polar prt_brk2 (+ prt_angbase (/ pi 2)) prt_wall)
	  prt_brk4b (polar prt_brk2 (- prt_angbase (/ pi 2)) prt_wall)
    )
  )
  (if (/= nil (ssget "_f" (list prt_brk3a prt_brk4a) (list (cons 8 prt_wall_layer))))
    (progn
      (setq prt_brk3 prt_brk3a prt_brk4 prt_brk4a prt_xcode 1)
      (setq prt_brkm (polar prt_brk3 (angle prt_brk3 prt_brk4) (/ (distance prt_brk3 prt_brk4) 2)))
      (if (= nil (ssget "c" prt_brkm prt_brkm))
	(progn
	  (setq prt_brk3 prt_brk3b prt_brk4 prt_brk4b)
	  (setq prt_brkm (polar prt_brk3 (angle prt_brk3 prt_brk4) (/ (distance prt_brk3 prt_brk4) 2))
		prt_xcode 2)
	)
      )
    )
    (progn
      (setq prt_brk3 prt_brk3b prt_brk4 prt_brk4b prt_xcode 2)
      (setq prt_brkm (polar prt_brk3 (angle prt_brk3 prt_brk4) (/ (distance prt_brk3 prt_brk4) 2)))
      (if (= nil (ssget "c" prt_brkm prt_brkm))
	(progn
	  (setq prt_brk3 prt_brk3a prt_brk4 prt_brk4a)
	  (setq prt_brkm (polar prt_brk3 (angle prt_brk3 prt_brk4) (/ (distance prt_brk3 prt_brk4) 2))
		prt_xcode 4)
	)
      )
    )
  )
  (setq colmo (getvar "cecolor"))
  (command "._undo" "_m")
  (command "._break" prt_ent1 "_non" prt_brk1 "_non" prt_brk2)
  (command "._break" (ssget "c" prt_brkm prt_brkm) "_non" prt_brk3 "_non" prt_brk4)
  (command "._layer" "_s" prt_wall_layer "")
  (command "._line" "_non" prt_brk1 "_non" prt_brk3 "" "._line" "_non" prt_brk2 "_non" prt_brk4 "")
  (setq prt_angortho (angle prt_brk1 prt_brk3))
)



;***********************************
;Porta Tipo 41                      
;Parte 01 - Configuração            
;***********************************
(defun prt_cfg_41 ()
  (prt_pt41_file)
  (setq dcl_id (load_dialog (strcat cnp_root "/lisp/cadnorma.dcl")))
  (if (not (new_dialog "prt_cfg_p41" dcl_id)) (exit))
  (set_tile "prt_descr" "Porta de correr dupla articulada.")
  ;slide de tipo
  (setq x (dimx_tile "prt_41_slide")
	y (dimy_tile "prt_41_slide")
  )
  (start_image "prt_41_slide")
  (fill_image 0 0 x y -2)
  (slide_image 0 0 x y (strcat cnp_root "/slides/prt_" prt_var_tipo ".sld"))
  (end_image)
  ;espessura da porta
  (set_tile "prt_41_poe_edit" prt_pt41_poe)
  (action_tile "prt_41_poe_edit" "(prt_41_poe_edit_act)")
  (action_tile "prt_41_poe_pick" "(done_dialog 2)")
  ;soleira
  (if (= "1" prt_pt41_soi) (set_tile "prt_41_solint"  "1"))
  (action_tile "prt_41_solint"  "(setq prt_pt41_soi $value)")
  (if (= "1" prt_pt41_soe) (set_tile "prt_41_solext"  "1"))
  (action_tile "prt_41_solext"  "(setq prt_pt41_soe $value)")
  ;alisares
  (if (= "1" prt_pt41_ali) (set_tile "prt_41_aliint"  "1"))
  (action_tile "prt_41_aliint"  "(setq prt_pt41_ali $value)")
  (if (= "1" prt_pt41_ale) (set_tile "prt_41_aliext"  "1"))
  (action_tile "prt_41_aliext"  "(setq prt_pt41_ale $value)")
  ;ok_cancel
  (action_tile "cancel" "(done_dialog 0)")
  (action_tile "accept" "(done_dialog 1)")
  ;start_dialog
  (setq prt_41_id (start_dialog))
  (unload_dialog dcl_id)
  (if (= prt_41_id 1) (prt_pt41_writefile))
  (if (= prt_41_id 2) (prt_41_poe_button_act))
)

;Espessura por Pick Points
(defun prt_41_poe_button_act ()
  (prt_pt41_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt41_poe (rtos new_dist 2 2))
      (prt_pt41_writefile)
    )
  )
  (prt_cfg_41)
)

;verifica se o valor de espessura entrado é válido
(defun prt_41_poe_edit_act ()
  (setq prt_var_newpoe $value)
  (if (distof prt_var_newpoe)
    (progn
      (setq prt_pt41_poe prt_var_newpoe)
      (prt_pt41_writefile)
    )
    (progn
      (alert "Valor Inválido!")
      (set_tile "prt_41_poe_edit" prt_pt41_poe)
      (mode_tile "prt_41_poe_edit" 2)
    )
  )
)  


;lê os dados iniciais da DCL no arquivo de dados
(defun prt_pt41_file ()
  (if (findfile (strcat cnp_root "/config/prt_pt41.txt"))
    (prt_pt41_readfile)
    (progn
      (setq file (open (strcat cnp_root "/config/prt_pt41.txt") "w" "utf8"))
      (write-line "1" file)
      (write-line "1" file)      
      (write-line "1" file)
      (write-line "1" file)
      (write-line "3" file)
      (close file)
      (prt_pt41_readfile)
    )
  )
)

;função que lê o arquivo de dados
(defun prt_pt41_readfile ()
  (setq	file (open (strcat cnp_root "/config/prt_pt41.txt") "r" "utf8"))
  (setq	prt_pt41_soi (read-line file))
  (setq	prt_pt41_soe (read-line file))
  (setq	prt_pt41_ali (read-line file))
  (setq	prt_pt41_ale (read-line file))
  (setq	prt_pt41_poe (read-line file))
  (close file)
)

;função que escreve o arquivo de dados
(defun prt_pt41_writefile ()
  (setq	file (open (strcat cnp_root "/config/prt_pt41.txt") "w" "utf8"))
  (write-line prt_pt41_soi file)
  (write-line prt_pt41_soe file)
  (write-line prt_pt41_ali file)
  (write-line prt_pt41_ale file)
  (write-line prt_pt41_poe file)
  (close file)
)

;Desenha a porta
(defun prt_drw41 ()
  (cn7_init)
  (guarda '("blipmode" "cecolor" "celtype" "clayer" "cmdecho" "orthomode"
          "textstyle" "luprec" "osmode" ))
  (setvar "cecolor" "bylayer")
  (prt_pt41_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 2.0)
  (prt_drw41_caixilho)
  (prt_drw41_soleira)
  (if (/= 0.0 prt_caix)
    (prt_drw41_alisar)
  )
  (prt_drw41_porta)
  (devolve)
  (prompt "\nUse o comando <UB> para retornar... ")
)

;*****************************************
;Desenho das Portas                       
;*****************************************
(defun prt_drw41_porta ()
  (setq prt_porta0 (polar prt_cxi1 prt_angortho (/ prt_wall 2.0))
	prt_porta1 (polar prt_porta0 (+ prt_angortho pi) (* prt_fator (distof prt_pt41_poe)))
	prt_porta2 (polar prt_porta1 (+ prt_angbase (/ pi 4)) (/ prt_larg 2.0))
	prt_porta3 (polar prt_porta2 (- prt_angbase (/ pi 4)) (* prt_fator (distof prt_pt41_poe)))
	prt_porta4 (polar prt_porta1 (- prt_angbase (/ pi 4)) (* prt_fator (distof prt_pt41_poe)))
	prt_porta5 (polar prt_porta3 (+ prt_angbase (/ pi 4)) (* prt_fator (distof prt_pt41_poe)))
	prt_porta6 (polar prt_porta5 (- prt_angbase (/ pi 4)) (/ prt_larg 2.0))
	prt_porta7 (polar prt_porta3 (- prt_angbase (/ pi 4)) (/ prt_larg 2.0))
  )
  (cn7_verylayer prt_layc_pol 7)
  (setvar "cecolor" prt_layc_poc)
  (command "._pline" "_non" prt_porta1 "_non" prt_porta2 "_non" prt_porta3 "_non" prt_porta4 "_c"
	   "._pline" "_non" prt_porta3 "_non" prt_porta5 "_non" prt_porta6 "_non" prt_porta7 "_c"
  )
)

;*****************************************
;Desenho das Alisares                     
;*****************************************
(defun prt_drw41_alisar ()
  (cn7_verylayer prt_layc_all 7)
  (setvar "cecolor" prt_layc_alc)
  ;internos
  (if (= "1" prt_pt41_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt41_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw41_soleira ()
  (cn7_verylayer prt_layc_sol 7)
  (setvar "cecolor" prt_layc_soc)
  (if (= prt_pt41_soi "1")
    (command "._line" "_non" prt_cxi1 "_non" prt_cxi2 "")
  )
  (if (= prt_pt41_soe "1")
    (command "._line" "_non" prt_cxi3 "_non" prt_cxi4 "")
  )
)

;*****************************************
;Desenho de Caixilho                      
;*****************************************

;desenha os caixihos
(defun prt_drw41_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 42                      
;Parte 01 - Configuração            
;***********************************
(defun prt_cfg_42 ()
  (prt_pt42_file)
  (setq dcl_id (load_dialog (strcat cnp_root "/lisp/cadnorma.dcl")))
  (if (not (new_dialog "prt_cfg_p42" dcl_id)) (exit))
  (set_tile "prt_descr" "Porta de correr quádrupla articulada.")
  ;slide de tipo
  (setq x (dimx_tile "prt_42_slide")
	y (dimy_tile "prt_42_slide")
  )
  (start_image "prt_42_slide")
  (fill_image 0 0 x y -2)
  (slide_image 0 0 x y (strcat cnp_root "/slides/prt_" prt_var_tipo ".sld"))
  (end_image)
  ;espessura da porta
  (set_tile "prt_42_poe_edit" prt_pt42_poe)
  (action_tile "prt_42_poe_edit" "(prt_42_poe_edit_act)")
  (action_tile "prt_42_poe_pick" "(done_dialog 2)")
  ;soleira
  (if (= "1" prt_pt42_soi) (set_tile "prt_42_solint"  "1"))
  (action_tile "prt_42_solint"  "(setq prt_pt42_soi $value)")
  (if (= "1" prt_pt42_soe) (set_tile "prt_42_solext"  "1"))
  (action_tile "prt_42_solext"  "(setq prt_pt42_soe $value)")
  ;alisares
  (if (= "1" prt_pt42_ali) (set_tile "prt_42_aliint"  "1"))
  (action_tile "prt_42_aliint"  "(setq prt_pt42_ali $value)")
  (if (= "1" prt_pt42_ale) (set_tile "prt_42_aliext"  "1"))
  (action_tile "prt_42_aliext"  "(setq prt_pt42_ale $value)")
  ;ok_cancel
  (action_tile "cancel" "(done_dialog 0)")
  (action_tile "accept" "(done_dialog 1)")
  ;start_dialog
  (setq prt_42_id (start_dialog))
  (unload_dialog dcl_id)
  (if (= prt_42_id 1) (prt_pt42_writefile))
  (if (= prt_42_id 2) (prt_42_poe_button_act))
)

;Espessura por Pick Points
(defun prt_42_poe_button_act ()
  (prt_pt42_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt42_poe (rtos new_dist 2 2))
      (prt_pt42_writefile)
    )
  )
  (prt_cfg_42)
)

;verifica se o valor de espessura entrado é válido
(defun prt_42_poe_edit_act ()
  (setq prt_var_newpoe $value)
  (if (distof prt_var_newpoe)
    (progn
      (setq prt_pt42_poe prt_var_newpoe)
      (prt_pt42_writefile)
    )
    (progn
      (alert "Valor Inválido!")
      (set_tile "prt_42_poe_edit" prt_pt42_poe)
      (mode_tile "prt_42_poe_edit" 2)
    )
  )
)  


;lê os dados iniciais da DCL no arquivo de dados
(defun prt_pt42_file ()
  (if (findfile (strcat cnp_root "/config/prt_pt42.txt"))
    (prt_pt42_readfile)
    (progn
      (setq file (open (strcat cnp_root "/config/prt_pt42.txt") "w" "utf8"))
      (write-line "1" file)
      (write-line "1" file)      
      (write-line "1" file)
      (write-line "1" file)
      (write-line "3" file)
      (close file)
      (prt_pt42_readfile)
    )
  )
)

;função que lê o arquivo de dados
(defun prt_pt42_readfile ()
  (setq	file (open (strcat cnp_root "/config/prt_pt42.txt") "r" "utf8"))
  (setq	prt_pt42_soi (read-line file))
  (setq	prt_pt42_soe (read-line file))
  (setq	prt_pt42_ali (read-line file))
  (setq	prt_pt42_ale (read-line file))
  (setq	prt_pt42_poe (read-line file))
  (close file)
)

;função que escreve o arquivo de dados
(defun prt_pt42_writefile ()
  (setq	file (open (strcat cnp_root "/config/prt_pt42.txt") "w" "utf8"))
  (write-line prt_pt42_soi file)
  (write-line prt_pt42_soe file)
  (write-line prt_pt42_ali file)
  (write-line prt_pt42_ale file)
  (write-line prt_pt42_poe file)
  (close file)
)

;Desenha a porta
(defun prt_drw42 ()
  (cn7_init)
  (guarda '("blipmode" "cecolor" "celtype" "clayer" "cmdecho" "orthomode"
          "textstyle" "luprec" "osmode" ))
  (setvar "cecolor" "bylayer")
  (prt_pt42_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 4.0)
  (prt_drw42_caixilho)
  (prt_drw42_soleira)
  (if (/= 0.0 prt_caix)
    (prt_drw42_alisar)
  )
  (prt_drw42_porta)
  (devolve)
  (prompt "\nUse o comando <UB> para retornar... ")
)


;*****************************************
;Desenho das Portas                       
;*****************************************
(defun prt_drw42_porta ()
  (setq s1 (ssadd)
	prt_porta0 (polar prt_cxi1 prt_angortho (/ prt_wall 2.0))
	prt_porta1 (polar prt_porta0 (+ prt_angortho pi) (* prt_fator (distof prt_pt42_poe)))
	prt_porta2 (polar prt_porta1 (+ prt_angbase (/ pi 4)) (/ prt_larg 4.0))
	prt_porta3 (polar prt_porta2 (- prt_angbase (/ pi 4)) (* prt_fator (distof prt_pt42_poe)))
	prt_porta4 (polar prt_porta1 (- prt_angbase (/ pi 4)) (* prt_fator (distof prt_pt42_poe)))
	prt_porta5 (polar prt_porta3 (+ prt_angbase (/ pi 4)) (* prt_fator (distof prt_pt42_poe)))
	prt_porta6 (polar prt_porta5 (- prt_angbase (/ pi 4)) (/ prt_larg 4.0))
	prt_porta7 (polar prt_porta3 (- prt_angbase (/ pi 4)) (/ prt_larg 4.0))
  )
  (cn7_verylayer prt_layc_pol 7)
  (setvar "cecolor" prt_layc_poc)
  (command "._pline" "_non" prt_porta1 "_non" prt_porta2 "_non" prt_porta3 "_non" prt_porta4 "_c")
  (setq s1 (ssadd (entlast) s1))
  (command "._pline" "_non" prt_porta3 "_non" prt_porta5 "_non" prt_porta6 "_non" prt_porta7 "_c")
  (setq s1 (ssadd (entlast) s1))
  (command ".mirror" s1 "" "_non" prt_mid1 "_non" prt_mid2 "_n")
)

;*****************************************
;Desenho das Alisares                     
;*****************************************
(defun prt_drw42_alisar ()
  (cn7_verylayer prt_layc_all 7)
  (setvar "cecolor" prt_layc_alc)
  ;internos
  (if (= "1" prt_pt42_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt42_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw42_soleira ()
  (cn7_verylayer prt_layc_sol 7)
  (setvar "cecolor" prt_layc_soc)
  (if (= prt_pt42_soi "1")
    (command "._line" "_non" prt_cxi1 "_non" prt_cxi2 "")
  )
  (if (= prt_pt42_soe "1")
    (command "._line" "_non" prt_cxi3 "_non" prt_cxi4 "")
  )
)

;*****************************************
;Desenho de Caixilho                      
;*****************************************

;desenha os caixihos
(defun prt_drw42_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 43                      
;Parte 01 - Configuração            
;***********************************
(defun prt_cfg_43 ()
  (prt_pt43_file)
  (setq dcl_id (load_dialog (strcat cnp_root "/lisp/cadnorma.dcl")))
  (if (not (new_dialog "prt_cfg_p43" dcl_id)) (exit))
  (set_tile "prt_descr" "Porta simples, de abrir para os dois lados")
  ;slide de tipo
  (setq x (dimx_tile "prt_43_slide")
	y (dimy_tile "prt_43_slide")
  )
  (start_image "prt_43_slide")
  (fill_image 0 0 x y -2)
  (slide_image 0 0 x y (strcat cnp_root "/slides/prt_" prt_var_tipo ".sld"))
  (end_image)
  ;espessura da porta
  (set_tile "prt_43_poe_edit" prt_pt43_poe)
  (action_tile "prt_43_poe_edit" "(prt_43_poe_edit_act)")
  (action_tile "prt_43_poe_pick" "(done_dialog 2)")
  ;soleira
  (if (= "1" prt_pt43_soi) (set_tile "prt_43_solint"  "1"))
  (action_tile "prt_43_solint"  "(setq prt_pt43_soi $value)")
  (if (= "1" prt_pt43_soe) (set_tile "prt_43_solext"  "1"))
  (action_tile "prt_43_solext"  "(setq prt_pt43_soe $value)")
  ;alisares
  (if (= "1" prt_pt43_ali) (set_tile "prt_43_aliint"  "1"))
  (action_tile "prt_43_aliint"  "(setq prt_pt43_ali $value)")
  (if (= "1" prt_pt43_ale) (set_tile "prt_43_aliext"  "1"))
  (action_tile "prt_43_aliext"  "(setq prt_pt43_ale $value)")
  ;ok_cancel
  (action_tile "cancel" "(done_dialog 0)")
  (action_tile "accept" "(done_dialog 1)")
  ;start_dialog
  (setq prt_43_id (start_dialog))
  (unload_dialog dcl_id)
  (if (= prt_43_id 1) (prt_pt43_writefile))
  (if (= prt_43_id 2) (prt_43_poe_button_act))
)

;Espessura por Pick Points
(defun prt_43_poe_button_act ()
  (prt_pt43_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt43_poe (rtos new_dist 2 2))
      (prt_pt43_writefile)
    )
  )
  (prt_cfg_43)
)

;verifica se o valor de espessura entrado é válido
(defun prt_43_poe_edit_act ()
  (setq prt_var_newpoe $value)
  (if (distof prt_var_newpoe)
    (progn
      (setq prt_pt43_poe prt_var_newpoe)
      (prt_pt43_writefile)
    )
    (progn
      (alert "Valor Inválido!")
      (set_tile "prt_43_poe_edit" prt_pt43_poe)
      (mode_tile "prt_43_poe_edit" 2)
    )
  )
)  


;lê os dados iniciais da DCL no arquivo de dados
(defun prt_pt43_file ()
  (if (findfile (strcat cnp_root "/config/prt_pt43.txt"))
    (prt_pt43_readfile)
    (progn
      (setq file (open (strcat cnp_root "/config/prt_pt43.txt") "w" "utf8"))
      (write-line "1" file)
      (write-line "1" file)      
      (write-line "1" file)
      (write-line "1" file)
      (write-line "3" file)
      (close file)
      (prt_pt43_readfile)
    )
  )
)

;função que lê o arquivo de dados
(defun prt_pt43_readfile ()
  (setq	file (open (strcat cnp_root "/config/prt_pt43.txt") "r" "utf8"))
  (setq	prt_pt43_soi (read-line file))
  (setq	prt_pt43_soe (read-line file))
  (setq	prt_pt43_ali (read-line file))
  (setq	prt_pt43_ale (read-line file))
  (setq	prt_pt43_poe (read-line file))
  (close file)
)

;função que escreve o arquivo de dados
(defun prt_pt43_writefile ()
  (setq	file (open (strcat cnp_root "/config/prt_pt43.txt") "w" "utf8"))
  (write-line prt_pt43_soi file)
  (write-line prt_pt43_soe file)
  (write-line prt_pt43_ali file)
  (write-line prt_pt43_ale file)
  (write-line prt_pt43_poe file)
  (close file)
)

;Desenha a porta
(defun prt_drw43 ()
  (cn7_init)
  (guarda '("blipmode" "cecolor" "celtype" "clayer" "cmdecho" "orthomode"
          "textstyle" "luprec" "osmode" ))
  (setvar "cecolor" "bylayer")
  (prt_pt43_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 1.0)
  (prt_drw43_caixilho)
  (prt_drw43_soleira)
  (if (/= 0.0 prt_caix)
    (prt_drw43_alisar)
  )
  (prt_drw43_porta)
  (devolve)
  (prompt "\nUse o comando <UB> para retornar... ")
)

;*****************************************
;Desenho das Portas                       
;*****************************************
(defun prt_drw43_porta ()
  (setq prt_porta0 (polar prt_cxi1 prt_angortho (/ prt_wall 2.0))
	prt_porta1 prt_porta0 ;(polar prt_porta0 (+ prt_angortho pi) (* prt_fator (cos (/ pi 4)) (distof prt_pt43_poe)))
	prt_porta2 (polar prt_porta1 (+ prt_angbase (/ pi 4)) prt_larg)
	prt_porta3 (polar prt_porta2 (- prt_angbase (/ pi 4)) (* prt_fator (distof prt_pt43_poe)))
	prt_porta4 (polar prt_porta1 (- prt_angbase (/ pi 4)) (* prt_fator (distof prt_pt43_poe)))
  )
  (cn7_verylayer prt_layc_pol 7)
  (setvar "cecolor" prt_layc_poc)
  (command "._pline" "_non" prt_porta1 "_non" prt_porta2 "_non" prt_porta3 "_non" prt_porta4 "_c"
	   "._mirror" (entlast) "" "_non" prt_porta0 "_non" (polar prt_porta0 prt_angbase 1.0) "_n"
  )
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (command "._chprop" (entlast) "" "_c" prt_layc_arc "_lt" "hidden2" "")
  (setq prt_porta0a prt_porta0 ;(polar prt_porta0 prt_angortho (* prt_fator (cos (/ pi 4)) (distof prt_pt43_poe)))
	prt_porta0b (polar prt_porta0a (+ prt_angbase (/ pi 4)) (* prt_fator (distof prt_pt43_poe)))
	prt_porta0c (polar prt_porta0b (- prt_angbase (/ pi 4)) prt_larg)
	prt_porta0d (polar prt_porta0 prt_angbase prt_larg)
  )
  (setvar "celtype" "hidden2")
  (cn7_verylayer prt_layc_arl 7)
  (setvar "cecolor" prt_layc_arc)
  (command "._arc" "_non" prt_porta0c "_non" prt_porta0d "_non" prt_porta3)
  (setvar "celtype" "bylayer")

)

;*****************************************
;Desenho das Alisares                     
;*****************************************
(defun prt_drw43_alisar ()
  (cn7_verylayer prt_layc_all 7)
  (setvar "cecolor" prt_layc_alc)
  ;internos
  (if (= "1" prt_pt43_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt43_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw43_soleira ()
  (cn7_verylayer prt_layc_sol 7)
  (setvar "cecolor" prt_layc_soc)
  (if (= prt_pt43_soi "1")
    (command "._line" "_non" prt_cxi1 "_non" prt_cxi2 "")
  )
  (if (= prt_pt43_soe "1")
    (command "._line" "_non" prt_cxi3 "_non" prt_cxi4 "")
  )
)

;*****************************************
;Desenho de Caixilho                      
;*****************************************

;desenha os caixihos
(defun prt_drw43_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)



;***********************************
;Porta Tipo 44                      
;Parte 01 - Configuração            
;***********************************
(defun prt_cfg_44 ()
  (prt_pt44_file)
  (setq dcl_id (load_dialog (strcat cnp_root "/lisp/cadnorma.dcl")))
  (if (not (new_dialog "prt_cfg_p44" dcl_id)) (exit))
  (set_tile "prt_descr" "Porta dupla, de abrir para os dois lados")
  ;slide de tipo
  (setq x (dimx_tile "prt_44_slide")
	y (dimy_tile "prt_44_slide")
  )
  (start_image "prt_44_slide")
  (fill_image 0 0 x y -2)
  (slide_image 0 0 x y (strcat cnp_root "/slides/prt_" prt_var_tipo ".sld"))
  (end_image)
  ;espessura da porta
  (set_tile "prt_44_poe_edit" prt_pt44_poe)
  (action_tile "prt_44_poe_edit" "(prt_44_poe_edit_act)")
  (action_tile "prt_44_poe_pick" "(done_dialog 2)")
  ;soleira
  (if (= "1" prt_pt44_soi) (set_tile "prt_44_solint"  "1"))
  (action_tile "prt_44_solint"  "(setq prt_pt44_soi $value)")
  (if (= "1" prt_pt44_soe) (set_tile "prt_44_solext"  "1"))
  (action_tile "prt_44_solext"  "(setq prt_pt44_soe $value)")
  ;alisares
  (if (= "1" prt_pt44_ali) (set_tile "prt_44_aliint"  "1"))
  (action_tile "prt_44_aliint"  "(setq prt_pt44_ali $value)")
  (if (= "1" prt_pt44_ale) (set_tile "prt_44_aliext"  "1"))
  (action_tile "prt_44_aliext"  "(setq prt_pt44_ale $value)")
  ;ok_cancel
  (action_tile "cancel" "(done_dialog 0)")
  (action_tile "accept" "(done_dialog 1)")
  ;start_dialog
  (setq prt_44_id (start_dialog))
  (unload_dialog dcl_id)
  (if (= prt_44_id 1) (prt_pt44_writefile))
  (if (= prt_44_id 2) (prt_44_poe_button_act))
)

;Espessura por Pick Points
(defun prt_44_poe_button_act ()
  (prt_pt44_writefile)
  (setq poe_dist nil
	pt1 (getpoint "\nPrimeiro ponto da espessura da porta...: ")
	pt2 (getpoint pt1 "Segundo ponto da espessura da porta...: ")
	poe_dist (distance pt1 pt2)
  )
  (cond
    ((= cn7_dwgunit 1.0) (setq new_dist (* poe_dist 100.0)))
    ((= cn7_dwgunit 100.0) (setq new_dist (* poe_dist 1.0)))
    ((= cn7_dwgunit 1000.0) (setq new_dist (* poe_dist 0.1)))
  )
  (if new_dist
    (progn
      (setq prt_pt44_poe (rtos new_dist 2 2))
      (prt_pt44_writefile)
    )
  )
  (prt_cfg_44)
)

;verifica se o valor de espessura entrado é válido
(defun prt_44_poe_edit_act ()
  (setq prt_var_newpoe $value)
  (if (distof prt_var_newpoe)
    (progn
      (setq prt_pt44_poe prt_var_newpoe)
      (prt_pt44_writefile)
    )
    (progn
      (alert "Valor Inválido!")
      (set_tile "prt_44_poe_edit" prt_pt44_poe)
      (mode_tile "prt_44_poe_edit" 2)
    )
  )
)  


;lê os dados iniciais da DCL no arquivo de dados
(defun prt_pt44_file ()
  (if (findfile (strcat cnp_root "/config/prt_pt44.txt"))
    (prt_pt44_readfile)
    (progn
      (setq file (open (strcat cnp_root "/config/prt_pt44.txt") "w" "utf8"))
      (write-line "1" file)
      (write-line "1" file)      
      (write-line "1" file)
      (write-line "1" file)
      (write-line "3" file)
      (close file)
      (prt_pt44_readfile)
    )
  )
)

;função que lê o arquivo de dados
(defun prt_pt44_readfile ()
  (setq	file (open (strcat cnp_root "/config/prt_pt44.txt") "r" "utf8"))
  (setq	prt_pt44_soi (read-line file))
  (setq	prt_pt44_soe (read-line file))
  (setq	prt_pt44_ali (read-line file))
  (setq	prt_pt44_ale (read-line file))
  (setq	prt_pt44_poe (read-line file))
  (close file)
)

;função que escreve o arquivo de dados
(defun prt_pt44_writefile ()
  (setq	file (open (strcat cnp_root "/config/prt_pt44.txt") "w" "utf8"))
  (write-line prt_pt44_soi file)
  (write-line prt_pt44_soe file)
  (write-line prt_pt44_ali file)
  (write-line prt_pt44_ale file)
  (write-line prt_pt44_poe file)
  (close file)
)

;programa de portas
;Desenha a porta
(defun prt_drw44 ()
  (cn7_init)
  (guarda '("blipmode" "cecolor" "celtype" "clayer" "cmdecho" "orthomode"
          "textstyle" "luprec" "osmode" ))
  (setvar "cecolor" "bylayer")
  (prt_pt44_file)
  (prt_last_file)
  (prt_layc_file)
  (prt_iden_file)
  (cond
    ((= cn7_dwgunit 1) (setq prt_fator 0.01 prt_blkscl 1.0))
    ((= cn7_dwgunit 100) (setq prt_fator 1.0 prt_blkscl 100.0))
    ((= cn7_dwgunit 1000) (setq prt_fator 10.0 prt_blkscl 1000.0))
  )
  ;abre o espaço
  (prt_openfree 2.0)
  (prt_drw44_caixilho)
  (prt_drw44_soleira)
  (if (/= 0.0 prt_caix)
    (prt_drw44_alisar)
  )
  (prt_drw44_porta)
  (devolve)
  (prompt "\nUse o comando <UB> para retornar... ")
)

;*****************************************
;Desenho das Portas                       
;*****************************************
(defun prt_drw44_porta ()
  (setq prt_porta0 (polar prt_cxi1 prt_angortho (/ prt_wall 2.0))
	prt_porta1 prt_porta0 
	prt_porta2 (polar prt_porta1 (+ prt_angbase (/ pi 4)) (/ prt_larg 2.0))
	prt_porta3 (polar prt_porta2 (- prt_angbase (/ pi 4)) (* prt_fator (distof prt_pt44_poe)))
	prt_porta4 (polar prt_porta1 (- prt_angbase (/ pi 4)) (* prt_fator (distof prt_pt44_poe)))
  )
  (cn7_verylayer prt_layc_pol 7)
  (setvar "cecolor" prt_layc_poc)
  (setq s1 (ssadd))
  (command "._pline" "_non" prt_porta1 "_non" prt_porta2 "_non" prt_porta3 "_non" prt_porta4 "_c")
  (setq s1 (ssadd (entlast) s1))
  (command "._mirror" (entlast) "" "_non" prt_porta0 "_non" (polar prt_porta0 prt_angbase 1.0) "_n")
  (setq s1 (ssadd (entlast) s1))
  (if (not (tblsearch "ltype" "hidden2"))
    (command "._linetype" "_l" "hidden2" (strcat cnp_root "/modelos/cadnorma.lin") "")
    (command "._linetype" "_l" "hidden2" (strcat cnp_root "/modelos/cadnorma.lin") "_y" "")
  )
  (command "._chprop" (entlast) "" "_c" prt_layc_arc "_lt" "hidden2" "")
  (setq prt_porta0a prt_porta0 
	prt_porta0b (polar prt_porta0a (+ prt_angbase (/ pi 4)) (* prt_fator (distof prt_pt44_poe)))
	prt_porta0c (polar prt_porta0b (- prt_angbase (/ pi 4)) (/ prt_larg 2.0))
	prt_porta0d (polar prt_porta0 prt_angbase (/ prt_larg 2.0))
  )
  (setvar "celtype" "hidden2")
  (cn7_verylayer prt_layc_arl 7)
  (setvar "cecolor" prt_layc_arc)
  (command "._arc" "_non" prt_porta0c "_non" prt_porta0d "_non" prt_porta3)
  (setq s1 (ssadd (entlast) s1))
  (setvar "celtype" "bylayer")
  (command "._mirror" s1 "" "_non" prt_mid1 "_non" prt_mid2 "_n")
)

;*****************************************
;Desenho das Alisares                     
;*****************************************
(defun prt_drw44_alisar ()
  (cn7_verylayer prt_layc_all 7)
  (setvar "cecolor" prt_layc_alc)
  ;internos
  (if (= "1" prt_pt44_ali)
    (progn
      (setq prt_ali_a1 (polar prt_cxi1 (+ prt_angbase pi) (* 1.0 prt_fator))
	    prt_ali_a2 (polar prt_ali_a1 (+ prt_angortho pi) (* 1.0 prt_fator))
	    prt_ali_a3 (polar prt_ali_a2 (+ prt_angbase pi) (* 5.0 prt_fator))
	    prt_ali_a4 (polar prt_ali_a3 prt_angortho (* 1.0 prt_fator))
	    prt_ali_b1 (polar prt_cxi2 prt_angbase (* 1.0 prt_fator))
	    prt_ali_b2 (polar prt_ali_b1 (+ prt_angortho pi) (* 1.0 prt_fator))
	    prt_ali_b3 (polar prt_ali_b2 prt_angbase (* 5.0 prt_fator))
	    prt_ali_b4 (polar prt_ali_b3 prt_angortho (* 1.0 prt_fator))
      )
      (command "._line" "_non" prt_ali_a1 "_non" prt_ali_a2 "_non" prt_ali_a3 "_non" prt_ali_a4 "")
      (command "._line" "_non" prt_ali_b1 "_non" prt_ali_b2 "_non" prt_ali_b3 "_non" prt_ali_b4 "")
    )
  )
  (if (= "1" prt_pt44_ale)
    (progn
      (setq prt_ale_a1 (polar prt_cxi3 (+ prt_angbase pi) (* 1.0 prt_fator))
	    prt_ale_a2 (polar prt_ale_a1 prt_angortho (* 1.0 prt_fator))
	    prt_ale_a3 (polar prt_ale_a2 (+ prt_angbase pi) (* 5.0 prt_fator))
	    prt_ale_a4 (polar prt_ale_a3 (+ prt_angortho pi) (* 1.0 prt_fator))
	    prt_ale_b1 (polar prt_cxi4 prt_angbase (* 1.0 prt_fator))
	    prt_ale_b2 (polar prt_ale_b1 prt_angortho (* 1.0 prt_fator))
	    prt_ale_b3 (polar prt_ale_b2 prt_angbase (* 5.0 prt_fator))
	    prt_ale_b4 (polar prt_ale_b3 (+ prt_angortho pi) (* 1.0 prt_fator))
      )
      (command "._line" "_non" prt_ale_a1 "_non" prt_ale_a2 "_non" prt_ale_a3 "_non" prt_ale_a4 "")
      (command "._line" "_non" prt_ale_b1 "_non" prt_ale_b2 "_non" prt_ale_b3 "_non" prt_ale_b4 "")
    )
  )
)


;*****************************************
;Desenho das Soleiras                     
;*****************************************
(defun prt_drw44_soleira ()
  (cn7_verylayer prt_layc_sol 7)
  (setvar "cecolor" prt_layc_soc)
  (if (= prt_pt44_soi "1")
    (command "._line" "_non" prt_cxi1 "_non" prt_cxi2 "")
  )
  (if (= prt_pt44_soe "1")
    (command "._line" "_non" prt_cxi3 "_non" prt_cxi4 "")
  )
)

;*****************************************
;Desenho de Caixilho                      
;*****************************************

;desenha os caixihos
(defun prt_drw44_caixilho ()
  (cn7_verylayer prt_layc_cxl 7)
  (setvar "cecolor" prt_layc_cxc)
  (if (/= 0.0 prt_caix)
    (progn
      (setq prt_cxi1 (polar prt_brk1 prt_angbase prt_caix)
	    prt_cxi2 (polar prt_cxi1 prt_angbase prt_larg)
	    prt_cxi3 (polar prt_brk3 prt_angbase prt_caix)
	    prt_cxi4 (polar prt_cxi3 prt_angbase prt_larg)
      )
      (command "._pline"  "_non" prt_brk1 "_non" prt_cxi1  "_non" prt_cxi3 "_non" prt_brk3 "" ;"_c"
	       "._pline"  "_non" prt_brk2 "_non" prt_cxi2  "_non" prt_cxi4 "_non" prt_brk4 "" ;"_c"
      )
    )
    ;se o caixilho for nulo
    (progn
      (setq prt_cxi1 prt_brk1
	    prt_cxi2 prt_brk2
	    prt_cxi3 prt_brk3
	    prt_cxi4 prt_brk4
      )
    )
  )
)


;cnp_22



;******************************************************************************
;******************************************************************************
;Dutos e Tubos
;******************************************************************************
;******************************************************************************
;***************************************************************************************
;desenho de fiação
;***************************************************************************************
(defun c:fio () (setq psimb_txt nil) (elet_fiacao 1) (princ))
(defun c:fio2 () (setq psimb_txt nil) (elet_fiacao 2) (princ))


(defun elet_fiacao (fio_tipo)
  (guarda '("blipmode" "cecolor" "celtype" "clayer" "cmdecho" "orthomode"
          "textstyle" "luprec" "osmode" ))
  (setq osmo (getvar "osmode"))
  (setq grp_type "2")
  (cn7_find_blkscl)
  (setvar "osmode" 512)
  (setq p1 (getpoint "\nPonto Inicial... ")
	rang (getangle p1 "\nDireção para representação...(ENTER=0)"))
  (if (= rang nil) (setq rang 0.0))
  (setq	comb (getstring T "\nSequencia da combinacao... (N F T R C ou <ESPAÇO>) ")
	ptxt (polar p1 (+ rang (/ pi 2)) (* cn7_blkscl 0.25))
	n (strlen comb)
	k1 1
  )
  (setvar "osmode" 0)
  (cn7_verylayer (strcat cn7_prefixlay "Ele_circuitos") 2)
  (while (<= k1 n)
    (setq letra (substr comb k1 1))
    (fnt_decide1)
    (setq k1 (1+ k1))
  );while
  (fnt_write_txt)
  (devolve)
);defun fnt

(defun fnt_decide1 ()
  (cond
    ((= (strcase letra) "F") (fnt_desenha_f))
    ((= (strcase letra) "N") (fnt_desenha_n))
    ((= (strcase letra) "R") (fnt_desenha_r))
    ((= (strcase letra) "T")
     (if (= fio_tipo 2) (fnt_desenha_t) (fnt_desenha_t2)))
    ((= (strcase letra) "C") (fnt_desenha_c))
    ((= (strcase letra) " ") (fnt_espaco))
  );cond
);defun

;espaço em branco
(defun fnt_espaco ()
    (setq p1 (polar p1 rang (* cn7_blkscl 0.1)))
)

;fio neutro
(defun fnt_desenha_n ()
  (command "._insert" (strcat cnp_root "/blocos/ele_circ_n") "_s" cn7_blkscl p1 (/ (* rang 180) pi))
  (setq p1 (polar p1 rang (* cn7_blkscl 0.1)))
)

;fio fase
(defun fnt_desenha_f ()
  (command "._insert" (strcat cnp_root "/blocos/ele_circ_f") "_s" cn7_blkscl p1 (/ (* rang 180) pi))
  (setq p1 (polar p1 rang (* cn7_blkscl 0.1)))
)

;fio retorno
(defun fnt_desenha_r ()
  (command "._insert" (strcat cnp_root "/blocos/ele_circ_r") "_s" cn7_blkscl p1 (/ (* rang 180) pi))
  (setq p1 (polar p1 rang (* cn7_blkscl 0.1)))
)

;fio terra tipo 1
(defun fnt_desenha_t ()
  (command "._insert" (strcat cnp_root "/blocos/ele_circ_t") "_s" cn7_blkscl p1 (/ (* rang 180) pi))
  (setq p1 (polar p1 rang (* cn7_blkscl 0.1)))
)

;fio terra tipo 2
(defun fnt_desenha_t2 ()
  (command "._insert" (strcat cnp_root "/blocos/ele_circ_t") "_s" cn7_blkscl p1 (/ (* rang 180) pi))
  (setq p1 (polar p1 rang (* cn7_blkscl 0.1)))
)

;fio de campainha
(defun fnt_desenha_c ()
  (command "._insert" (strcat cnp_root "/blocos/ele_circ_c") "_s" cn7_blkscl p1 (/ (* rang 180) pi))
  (setq p1 (polar p1 rang (* cn7_blkscl 0.1)))
)

;escreve texto da fiação
(defun fnt_write_txt ()
  (if psimb_txt
    (setq psimb_txt (getpoint psimb_txt "\nPosicao do texto...<ENTER para terminar>... "))
    (setq psimb_txt (getpoint "\nPosicao do texto...<ENTER para terminar>... "))
  )
  (if (= psimb_txt nil)
    (progn
      (setvar "osmode" osmo)
      (devolve)
      (exit)
      (princ)
    )
    (progn
      (setq ident (getstring "\nIdentificacao do circuito... "))
      (cn7_txsimb "r80" "c" ident 2 "Ele_circuitos" (rtos (/ (* 180 rang) pi) 2 4))
      (fnt_write_txt)
    );progn case F
  );if
  (setvar "osmode" osmo)
  (setvar "clayer" laymo)
);defun


;eletrodutos verticais
(defun c:eldv ()
  (guarda '("blipmode" "cecolor" "celtype" "clayer" "cmdecho" "orthomode"
          "textstyle" "luprec" "osmode" ))
  (setq grp_type "2")
  (cn7_find_blkscl)
  (setvar "osmode" 0)
  (setq
    p1 (getpoint "\nPrimeiro ponto...")
    p2 (getpoint p1 "\nDireção...")
    angrad (angle p1 p2)
  )
  (initget "Sobe Desce Passa")
  (if (= nil eldv_resp)
    (progn
      (setq eldv_resp (getkword "\n<Sobe>/Desce/Passa...: "))
      (if (= nil eldv_resp) (setq eldv_resp "Sobe"))
    )
    (progn
      (cond
	((= eldv_resp "Sobe")
	 (setq eldv_resp (getkword "\n<Sobe>/Desce/Passa...: "))
	 (if (= nil eldv_resp) (setq eldv_resp "Sobe"))
	)
	((= eldv_resp "Desce")
	 (setq eldv_resp (getkword "\nSobe/<Desce>/Passa...: "))
	 (if (= nil eldv_resp) (setq eldv_resp "Desce"))
	)
	((= eldv_resp "Passa")
	 (setq eldv_resp (getkword "\nSobe/Desce/<Passa>...: "))
	 (if (= nil eldv_resp) (setq eldv_resp "Passa"))
	)
      )
    )
  )
  (cn7_verylayer (strcat cn7_prefixlay "Ele_verticais") 2)
  (cond
    ((= eldv_resp "Sobe")
     (setq p3 (polar p1 angrad (* cn7_blkscl 0.03))
	   p4 (polar p3 angrad (* cn7_blkscl 0.50))
	   p5 (polar p3 angrad (* cn7_blkscl 0.80)))
     (command "._circle" p1 (* cn7_blkscl 0.03)
	      "._pline" p3 "_w" "0.0" "0.0" p4 "_w" (* cn7_blkscl 0.1) "0.0" p5 ""))
    ((= eldv_resp "Desce")
     (setq p3 (polar p1 angrad (* cn7_blkscl 0.03))
	   p4 (polar p3 angrad (* cn7_blkscl 0.30))
	   p5 (polar p3 angrad (* cn7_blkscl 0.80)))
     (command "._circle" p1 (* cn7_blkscl 0.03)
	      "._pline" p3 "_w" "0.0" (* cn7_blkscl 0.1) p4 "_w" "0.0" "0.0" p5 ""))
    ((= eldv_resp "Passa")
     (setq p3 (polar p1 angrad (* cn7_blkscl 0.03))
	   p4 (polar p3 angrad (* cn7_blkscl 0.80))
	   p5 (polar p3 angrad (* cn7_blkscl 1.10))
	   p6 (polar p3 angrad (* cn7_blkscl 0.30)))
     (command "._circle" p1 (* cn7_blkscl 0.03)
	      "._pline" p3 "_w" "0.0" (* cn7_blkscl 0.1) p6 "_w" "0.0" "0.0" p4 "_w" (* cn7_blkscl 0.1) "0.0" p5 ""))
  )
  (devolve)
  (princ)
)

;diâmetro de tubos
(defun c:diatub ()
  (cn7_init)
  (guarda '("blipmode" "cecolor" "celtype" "clayer" "cmdecho" "orthomode"
          "textstyle" "luprec" "osmode" ))
  (setq grp_type "2")
  (cn7_find_blkscl)
  (setq osmo (getvar "osmode")
	laymo (getvar "clayer"))
  (setvar "osmode" 512)
  (setq
    p1 (getpoint "\nPonto de identificação...")
    p2 (getpoint p1 "\nSentido do Fluxo (Direção do Texto)...")
    angrad (angle p1 p2)
    angdeg (/ (* 180 angrad) pi)
    txt1 (getstring "\nDiâmetro (ENTER = nenhum)...: ")
  )
  (setvar "osmode" osmo)
  (if (/= txt1 "")
    (if (>= (cos angrad) 0)
      (progn
	(setq psimb_txt (polar p1 (+ angrad  (/ pi 2)) (* 0.15 cn7_blkscl)))
	(cn7_txsimb "r80" "c" (strcat "%%c" txt1) 3 "Tub_identificação" angdeg)
      )
      (progn
	(setq psimb_txt (polar p1 (- angrad  (/ pi 2)) (* 0.15 cn7_blkscl)))
	(cn7_txsimb "r80" "c" (strcat "%%c" txt1) 3 "Tub_identificação" (+ 180 angdeg))
      )
    )
  )
  (initget "Sim Não")
  (if (= nil diatub_resp)
    (progn
      (setq diatub_resp (getkword "\nDesenhar seta? <Sim>/Não...: "))
      (if (= nil diatub_resp) (setq diatub_resp "Sim"))
    )
    (progn
      (cond
	((= diatub_resp "Sim")
	 (setq diatub_resp (getkword "\nDesenhar seta? <Sim>/Não...: "))
	 (if (= nil diatub_resp) (setq diatub_resp "Sim"))
	)
	((= diatub_resp "Não")
	 (setq diatub_resp (getkword "\nDesenhar seta? Sim/<Não>...: "))
	 (if (= nil diatub_resp) (setq diatub_resp "Não"))
	)
      );cond
    )
  );if
  (if (= diatub_resp "Sim")
    (if (>= (cos angrad) 0)
      (progn
	(setq p3 (polar p1 (- angrad  (/ pi 2)) (* 0.15 cn7_blkscl))
	      p4 (polar p3 (+ angrad pi) (* 0.25 cn7_blkscl))
	      p5 (polar p3 angrad (* 0.25 cn7_blkscl))
	)
	(cn7_verylayer (strcat cn7_prefixlay "Tub_identificação")  3)
	(command "._pline" "_non" p5 "_w" 0 (* 0.1 cn7_blkscl) "_non" p3 "_w" 0 0 "_non" p4 "" "._chprop" (entlast) "" "_c" 2 "")
      )
      (progn
	(setq p3 (polar p1 (+ angrad  (/ pi 2)) (* 0.15 cn7_blkscl))
	      p4 (polar p3 (+ angrad pi) (* 0.25 cn7_blkscl))
	      p5 (polar p3 angrad (* 0.25 cn7_blkscl))
	)
	(cn7_verylayer (strcat cn7_prefixlay "Tub_identificação")  3)
	(command "._pline" "_non" p5 "_w" 0 (* 0.1 cn7_blkscl) "_non" p3 "_w" 0 0 "_non" p4 "" "._chprop" (entlast) "" "_c" 2 "")
      )
    )
  )
  (devolve)
  (princ)
)


;identificação de tubulações
(defun c:idtub ()
  (cn7_init)
  (guarda '("blipmode" "cecolor" "celtype" "clayer" "cmdecho" "orthomode"
          "textstyle" "luprec" "osmode" ))
  (setq grp_type "2")
  (cn7_find_blkscl)
  (setq osmo (getvar "osmode"))
  (setvar "osmode" 512)
  (setq
    p1 (getpoint "\nPonto de identificação...")
    p2 (getpoint p1 "\nSentido do Fluxo (Direção do Texto)...")
    angrad (angle p1 p2)
    angdeg (/ (* 180 angrad) pi)
    txt1 (getstring "\nDiâmetro (ENTER = nenhum)...: ")
    txt2 (getstring "\nTexto abaixo (ENTER = nenhum)...: ")
  )
  (setvar "osmode" osmo)
  (if (/= txt1 "")
    (if (>= (cos angrad) 0)
      (progn
	(setq psimb_txt (polar p1 (+ angrad  (/ pi 2)) (* 0.15 cn7_blkscl)))
	(cn7_txsimb "r80" "c" (strcat "%%c" txt1) 3 "Tub_identificação" angdeg)
	(setq txt_ent (entlast) txt_point psimb_txt)
      )
      (progn
	(setq psimb_txt (polar p1 (- angrad  (/ pi 2)) (* 0.15 cn7_blkscl)))
	(cn7_txsimb "r80" "c" (strcat "%%c" txt1) 3 "Tub_identificação" (+ 180 angdeg))
	(setq txt_ent (entlast) txt_point psimb_txt)
      )
    )
  )
  (if (/= txt2 "")
    (if (>= (cos angrad) 0)
      (progn
	(setq psimb_txt (polar p1 (- angrad  (/ pi 2)) (* 0.35 cn7_blkscl)))
	(cn7_txsimb "r80" "c" txt2 3 "Tub_identificação" angdeg)
      )
      (progn
	(setq psimb_txt (polar p1 (+ angrad  (/ pi 2)) (* 0.35 cn7_blkscl)))
	(cn7_txsimb "r80" "c" txt2 3 "Tub_identificação" (+ 180 angdeg))
      )
    )
  )
  (if (/= "" txt1)
    (progn
      (initget "Sim Não")
      (if (= nil idtub_resp)
	(progn
	  (setq idtub_resp (getkword "\nDesenhar seta? <Sim>/Não...: "))
	  (if (= nil idtub_resp) (setq idtub_resp "Sim"))
	  )
	(progn
	  (cond
	    ((= idtub_resp "Sim")
	     (setq idtub_resp (getkword "\nDesenhar seta? <Sim>/Não...: "))
	     (if (= nil idtub_resp) (setq idtub_resp "Sim"))
	    )
	    ((= idtub_resp "Não")
	     (setq idtub_resp (getkword "\nDesenhar seta? Sim/<Não>...: "))
	     (if (= nil idtub_resp) (setq idtub_resp "Não"))
	    )
	   );cond
	 )
      );if
      (if (= idtub_resp "Sim")
	(progn
	  (setq tb (textbox (entget txt_ent))
		ll (car tb)
		ur (cadr tb)
		lr (list (car ur) (cadr ll))
	  )
	  (if (>= (cos angrad) 0)
	    (progn
	      (setq p3a (polar txt_point angrad (+ (/ (distance ll lr) 2) (* 0.35 cn7_blkscl)))
		    p3 (polar p3a (+ angrad  (/ pi 2)) (* 0.1 cn7_blkscl))
		    p4 (polar p3 (+ angrad pi) (* 0.25 cn7_blkscl))
		    p5 (polar p3 angrad (* 0.25 cn7_blkscl))
	      )
	      (command "._pline" "_non" p5 "_w" 0 (* 0.1 cn7_blkscl) "_non" p3 "_w" 0 0 "_non" p4 "" "._chprop" (entlast) "" "_c" 2 "")
	    )
	    (progn
	      (setq p3a (polar txt_point angrad (+ (/ (distance ll lr) 2) (* 0.35 cn7_blkscl)))
		    p3 (polar p3a (- angrad  (/ pi 2)) (* 0.1 cn7_blkscl))
		    p4 (polar p3 (+ angrad pi) (* 0.25 cn7_blkscl))
		    p5 (polar p3 angrad (* 0.25 cn7_blkscl))
		    )
	      (command "._pline" "_non" p5 "_w" 0 (* 0.1 cn7_blkscl) "_non" p3 "_w" 0 0 "_non" p4 "" "._chprop" (entlast) "" "_c" 2 "")
	    )
	  )
	);progn
      )
    );progn
  );if
  (devolve)
  (princ)
)

;Desenha colunas
(defun c:descol ()
  (cn7_init)
  (guarda '("blipmode" "cecolor" "celtype" "clayer" "cmdecho" "orthomode"
	    "textstyle" "luprec" "osmode" "dimzin"))
  (setvar "cmdecho" 0)
  (setvar "orthomode" 0)
  (setq grp_type "2")
  (cn7_find_blkscl)
  (cn7_verylayer (strcat cn7_blk_prefixlay "Tub_verticais") 3)
  ;coleta os dados
  (setq pt1 (getpoint "\nEixo da Tubulação: ")
	pt2 (getpoint pt1 "\nPosição do Texto: "))
  (if (= dt nil)
    (while (= dt nil)
      (setq dt (getreal "\nDiâmetro doTubo (em mm)..."))
    )
    (setq dt (getreal (strcat "\nDiâmetro do Tubo (em mm)... <" (rtos dt) ">: ")))
  )
  (if (= dt nil)
    (setq dt dt1)
    (setq dt1 dt)
  )
  (if (= "" (setq sg (getstring "\nSigla da Tubulação (AF, TQ, ...): "))) (exit))
  ;processa os dados
  (setq ang1 (angle pt1 pt2))
  (if (= dt nil) (quit))
  (cond
    ((= cn7_dwgunit 1.0)   (setq dt2 (/ dt 1000)))
    ((= cn7_dwgunit 100.0) (setq dt2 (/ dt 10)))
    ((= cn7_dwgunit 1000.0) (setq dt2 dt))
  )
  (setvar "osmode" 0)
  (if (= ang1 nil) (setq ang1 0.0))
  (setq ang (rtos (* ang1 (/ 180 pi))))
  (if (= ang nil) (setq ang "0"))
  (setq dist1 (polar pt1 ang1 (/ dt2 2)))

  ;decide o tipo de representação
  (initget "Sobe Desce Passa")
  (if (= nil descol_resp)
    (progn
      (setq descol_resp (getkword "\n<Sobe>/Desce/Passa...: "))
      (if (= nil descol_resp) (setq descol_resp "Sobe"))
    )
    (progn
      (cond
	((= descol_resp "Sobe")
	 (setq descol_resp (getkword "\n<Sobe>/Desce/Passa...: "))
	 (if (= nil descol_resp) (setq descol_resp "Sobe"))
	)
	((= descol_resp "Desce")
	 (setq descol_resp (getkword "\nSobe/<Desce>/Passa...: "))
	 (if (= nil descol_resp) (setq descol_resp "Desce"))
	)
	((= descol_resp "Passa")
	 (setq descol_resp (getkword "\nSobe/Desce/<Passa>...: "))
	 (if (= nil descol_resp) (setq descol_resp "Passa"))
	)
      )
    )
  )
  (cn7_verylayer (strcat cn7_prefixlay "Tub_verticais") 3)
  (cond
    ((= descol_resp "Sobe")
     (setq pt3 (polar pt2 (angle pt2 dist1) (* cn7_blkscl 0.35)))
     (command "._circle" "_non" pt1 "_d" "_non" dt2 "._pline" "_non" dist1 "_w" "0.0" "0.0" "_non" pt3 "_w" (* cn7_blkscl 0.1) "0.0" "_non" pt2 ""))
    ((= descol_resp "Desce")
     (setq pt3 (polar dist1 (angle dist1 pt2) (* cn7_blkscl 0.35)))
     (command "._circle" "_non" pt1 "_d" dt2 "._pline" "_non" pt2 "_w" "0.0" "0.0" "_non" pt3 "_w" (* cn7_blkscl 0.1) "0.0" dist1 ""))
    ((= descol_resp "Passa")
     (command "._circle" "_non" pt1 "_d" dt2 "._pline" "_non" dist1 "_non" pt2 ""))
  )
  (if (>= (cos ang1) 0)
    (setq bloco (strcat cnp_root "/blocos/tub_tcol1"))
    (setq bloco (strcat cnp_root "/blocos/tub_tcol2"))
  )
  (setq attdia_mode (getvar "attdia"))
  (setvar "attdia" 0)
  (setvar "dimzin" 8)
  (command "._insert" bloco "_non" pt2 cn7_blkscl "" 0 sg (strcat "%%c" (rtos dt)))
  (setvar "attdia" attdia_mode)
  (devolve)
  (princ)
)


(defun c:idcol ()
  (cn7_init)
  (guarda '("blipmode" "cecolor" "celtype" "clayer" "cmdecho" "orthomode"
          "textstyle" "luprec" "osmode" ))
  (setq grp_type "2")
  (cn7_find_blkscl)
  (setq osmo (getvar "osmode"))
  (setvar "osmode" 512)
  (setq
    p1 (getpoint "\nPonto de identificação...")
    p2 (getpoint p1 "\nPosição da Legenda...")
    angrad (angle p1 p2)
    angdeg (/ (* 180 angrad) pi)
    ttub (getstring "\nTipo de Tubulacao <ex. ES, AF, AQ...>...: ")
    dtub (strcat "%%c" (getstring "\nDiametro da Tubulacao <ex. 50>..."))
    p3 (polar p1 angrad (* cn7_blkscl 0.35))
    p4 (polar p2 (+ pi angrad) (* cn7_blkscl 0.95))
    p5 (polar p2 (+ pi angrad) (* cn7_blkscl 0.6))
    p6 (polar p2 angrad (* cn7_blkscl 0.6))
    p7 (polar p6 angrad (* cn7_blkscl 0.5))
  )
  (initget "Sobe Desce Passa")
  (if (= nil idcol_resp)
    (progn
      (setq idcol_resp (getkword "\n<Sobe>/Desce/Passa...: "))
      (if (= nil idcol_resp) (setq idcol_resp "Sobe"))
    )
    (progn
      (cond
	((= idcol_resp "Sobe")
	 (setq idcol_resp (getkword "\n<Sobe>/Desce/Passa...: "))
	 (if (= nil idcol_resp) (setq idcol_resp "Sobe"))
	)
	((= idcol_resp "Desce")
	 (setq idcol_resp (getkword "\nSobe/<Desce>/Passa...: "))
	 (if (= nil idcol_resp) (setq idcol_resp "Desce"))
	)
	((= idcol_resp "Passa")
	 (setq idcol_resp (getkword "\nSobe/Desce/<Passa>...: "))
	 (if (= nil idcol_resp) (setq idcol_resp "Passa"))
	)
      )
    )
  )
  (cn7_verylayer (strcat cn7_blk_prefixlay "Tub_verticais") 3)
  (setvar "osmode" 0)
  (cond
    ((= idcol_resp "Sobe") (command "._pline" p1 "_w" 0 0  p4 "_w" (* cn7_blkscl 0.1) 0 p5 ""))
    ((= idcol_resp "Desce") (command "._pline" p1 "_w" 0 (* cn7_blkscl 0.1)  p3 "_w" 0 0 p5 ""))
    ((= idcol_resp "Passa") (command "._pline" p1 p5 ""))
  )
  (command "._pline" p6 p7 "")
  (command "._insert" (strcat cnp_root "/blocos/idcol") "_s" cn7_blkscl p2 0 ttub dtub)
  (devolve)
  (princ)
)


(DEFUN c:TISO	(/ s1 p1 expert osmode)
  (SETVAR "CMDECHO" 0)
  ;; Desligar o echo dos comandos
  (IF ;; Se o ponto p1 for fornecido
      (SETQ
	p1 (GETPOINT
	     (STRCAT "\n-> Selecione o ponto base da "
		     "transformação de planta baixa em isométrico :  "
	     )
	   )
      )
    (PROGN ;; Então executar as expressões seguintes :
	   (SETQ expert	(GETVAR "EXPERT")
		 osmode	(GETVAR "OSMODE")
	   )
	   ;; Salvar valores das variáveis de ambiente, para
	   ;; posterior restauração...
	   (SETVAR "EXPERT" 5)
	   (SETVAR "OSMODE" 0)
	   ;; Ajustar estas variáveis para os valores
	   ;; adequados à rotina...
	   (PRINC "\n-> Selecione o objeto para virar isométrico : ")
	   ;; Informar ao usuário em PORTUGUÊS...
	   (SETQ s1 (SSGET))
	   ;; pois a mensagem de ssget é em inglês, pedindo ao
	   ;; usuário para selecionar entidades, que serão colocadas
	   ;; em vista isométrica em 2d e meio...
	   (IF s1
	     ;; Selecionou entidades? Então, prosseguir com a rotina...
	     (COMMAND "_.ROTATE"
		      s1
		      ""
		      p1
		      "-45"
		      "_.BLOCK"
		      "MY_TEMP_ISO"
		      p1
		      "_P"
		      ""
		      "_.INSERT"
		      "MY_TEMP_ISO"
		      p1
		      1.224744871391588
		      0.7071067811865475
		      ""
		      "_.EXPLODE"
		      (ENTLAST)
	     )
	     ;; Não selecionou, retornar 'nil' (ou nada)
	     nil
	   )
	   ;; Restaurar os valores originais das variáveis
	   ;; de sistema modificadas...
	   (SETVAR "EXPERT" expert)
	   (SETVAR "OSMODE" osmode)
    )
    ;; O ponto p1 não foi fornecido, então retornar 'nil'
    nil
  )
  ;; Limpar o prompt de qualquer retorno na saida e encerrar a rotina...
  (PRINC)
)

;cnp_23


;******************************************************************************
;******************************************************************************
;Aplicativos de Topografia
;******************************************************************************
;******************************************************************************

;***********  Lança as coordenadas norte e leste de um ponto selecionado   *************
(defun c:ne_dec () (setq ne_dec (getint "\nNúmero de casas decimais <0,1,2,...> : ")) (princ))

(defun c:ne ();(/ n e pt1 pt2 pt3 pt4 pt4i osmo)
  (cn7_init)
  (guarda '("blipmode" "cecolor" "celtype" "clayer" "cmdecho" "orthomode"
          "textstyle" "luprec" "osmode" ))
  (setq grp_type "2")
  (cn7_find_blkscl)
  (if (= nil ne_dec) (setq ne_dec (getint "\nNúmero de casas decimais <0,1,2,...> : ")))
  (setq osmo (getvar "osmode"))
  (setq laymo (getvar "clayer"))
  (initget 1)
  (setq pt1 (getpoint "\nOrigem da coordenada : "))
  (setq pt2 (getpoint pt1 "\nOnde  vai   escrever : ")
	e    (strcat "E: " (rtos (car  pt1) 2 ne_dec))
	n    (strcat "N: " (rtos (cadr pt1) 2 ne_dec))
        angrad (angle pt1 pt2)
        pt1a (polar pt1 angrad (* cn7_blkscl 0.2))
  )
  (if (>= (cos angrad) 0)
    (progn
      (setq pt3 (polar pt2 0 (* 0.2 cn7_blkscl))
	    pt4 (polar pt3 (/ pi 2) (* 0.1 cn7_blkscl))
	    )
      (setq psimb_txt pt4)
      (cn7_txsimb "r80" "" n 2 "Top_norte_leste" "0")
      (setq txt_ent (entlast)
	    tb (textbox (entget txt_ent))
	    ll (car tb)
	    ur (cadr tb)
	    lr (list (car ur) (cadr ll))
	    dist (distance ll lr)
      )
      (setq psimb_txt (polar psimb_txt (/ (* 3 pi) 2) (* 0.4 cn7_blkscl)))
      (cn7_txsimb "r80" "" e 2 "Top_norte_leste" "0")
      (cn7_verylayer (strcat cn7_prefixlay "Top_norte_leste") 2)
      (command "._pline" "_non" pt1 "_w" "0.0" (* cn7_blkscl 0.075) "_non" pt1a "_w" "0.0" "0.0" "_non" pt2 "_non" (polar pt3 0 (+ dist (* 0.2 cn7_blkscl)))
	       "" "._chprop" "_l" "" "_c" "1" "")
     )
    (progn
      (setq pt3 (polar pt2 pi (* 0.2 cn7_blkscl))
	    pt4 (polar pt3 (/ pi 2) (* 0.1 cn7_blkscl))
      )
      (setq psimb_txt pt4)
      (cn7_txsimb "r80" "" n 2 "Top_norte_leste" "0")
      (setq txt_ent (entlast)
	    tb (textbox (entget txt_ent))
	    ll (car tb)
	    ur (cadr tb)
	    lr (list (car ur) (cadr ll))
	    dist (distance ll lr)
	    ptxt (polar pt4 pi dist)
	    psimb_txt (polar ptxt (/ (* 3 pi) 2) (* 0.4 cn7_blkscl))
      )
      (command "._move" txt_ent "" "_non" pt4 "_non" ptxt)
      (cn7_txsimb "r80" "" e 2 "Top_norte_leste" "0")
      (command "._pline" "_non" pt1 "_w" "0.0" (* cn7_blkscl 0.075) "_non" pt1a "_w" "0.0" "0.0" "_non" pt2 "_non" (polar pt3 pi (+ dist (* 0.2 cn7_blkscl)))
	       "" "._chprop" "_l" "" "_c" "1" "")
    )      
  )
  (setvar "osmode" osmo)
  (setvar "clayer" laymo)
  (devolve)
  (princ)
)


(defun c:norte ()
  (cn7_init)
  (guarda '("blipmode" "cecolor" "celtype" "clayer" "cmdecho" "orthomode"
          "textstyle" "luprec" "osmode" ))
  (setq grp_type "2")
  (cn7_find_blkscl)
  (setq pt1 (getpoint "\nPonto a identificar a coordenada Norte..."))
  (if (= nil ne_dec) (setq ne_dec (getint "\nNúmero de casas decimais <0,1,2,...> : ")))
  (setq pt1_norte (rtos (nth 1 pt1) 2 ne_dec))
  (setq psimb_txt (polar pt1 (/ pi 4) (* 0.075 cn7_blkscl)))
  (cn7_txsimb "r80" "" pt1_norte 2 "Top_norte_leste" "0")
  (princ)
)

(defun c:leste ()
  (cn7_init)
  (guarda '("blipmode" "cecolor" "celtype" "clayer" "cmdecho" "orthomode"
          "textstyle" "luprec" "osmode" ))
  (setq grp_type "2")
  (cn7_find_blkscl)
  (setq pt1 (getpoint "\nPonto a identificar a coordenada Leste..."))
  (if (= nil ne_dec) (setq ne_dec (getint "\nNúmero de casas decimais <0,1,2,...> : ")))
  (setq pt1_leste (rtos (nth 0 pt1) 2 ne_dec))
  (setq psimb_txt (polar pt1 (* 3 (/ pi 4)) (* 0.075 cn7_blkscl)))
  (cn7_txsimb "r80" "" pt1_leste 2 "Top_norte_leste" "90")
  (devolve)
  (princ)
)


;;;;;;;;;;;;;;;;;;;;;;;;;;;MALHA DE COORDENADAS ;;;;;;;;;;;;;;;;;;;;;;;;;;;;;;;;;;;;;;
(defun c:malha ()
  (guarda '("blipmode" "cecolor" "celtype" "clayer" "cmdecho" "orthomode"
          "textstyle" "luprec" "osmode" ))
  (command "._undo" "_m")	
  (cn7_init)
  (setq grp_type "2")
  (cn7_find_blkscl)	
  (setq txtmo (getvar "textstyle")
	laymo (getvar "clayer")
	osmo (getvar "osmode")
	colmo (getvar "cecolor")
  )
  (setq amplitude (getint "\nAmplitude da malha..."))
  (setq pt1 (getpoint "\nPonto inferior esquerdo...")
	pt2 (getcorner pt1 "\nPonto superior direito...")
	xpt1 (nth 0 pt1)
	ypt1 (nth 1 pt1)
	xpt2 (nth 0 pt2)
	ypt2 (nth 1 pt2)
	xrpt1 (* amplitude (fix (/ (nth 0 pt1) amplitude)))
	yrpt1 (* amplitude (1- (fix (/ (nth 1 pt1) amplitude))))
	xrpt2 (* amplitude (1+ (fix (/ (nth 0 pt2) amplitude))))
	yrpt2 (* amplitude (1+ (fix (/ (nth 1 pt2) amplitude))))
	pm1 (polar (list xrpt1 yrpt1) pi (* 1.5 cn7_blkscl))
	pm2 (polar pm1 0 (+ (- xrpt2 xrpt1) (* 2 1.5 cn7_blkscl)))
	pm3 (polar (list xrpt1 yrpt1) (/ (* 3 pi) 2) (* 1.5 cn7_blkscl))
	pm4 (polar pm3 (/ pi 2) (+ (- yrpt2 yrpt1) (* 2 1.5 cn7_blkscl)))
	nx (1+ (/ (- xrpt2 xrpt1) amplitude))
	ny (1+ (/ (- yrpt2 yrpt1) amplitude))
  )
  (cn7_verylayer "Top_malha_coord" 2)
  (setvar "cecolor" "bylayer")
  (setvar "osmode" 0)
  (command "._line" pm1 pm2 "")
  (command "._array" (entlast) "" "_r" ny 1 amplitude)
  (command "._line" pm3 pm4 "")
  (command "._array" (entlast) "" "_r" 1 nx amplitude)
  (wtm_malha)
  (setvar "textstyle" txtmo)
  (setvar "clayer" laymo)
  (setvar "osmode" osmo)
  (setvar "cecolor" colmo)
  (devolve)
  (princ)
)

(defun wtm_malha ()
  (setq inicio xrpt1
	quant nx
	psimb_txt (polar pm3 pi (* 0.05 cn7_blkscl))
	dist amplitude
	ang_txt 90
	ang_dir 0
	increm amplitude
  )
  (wtm_malha_escreve)
  (setq inicio yrpt1
	quant ny
	psimb_txt (polar pm1 (/ pi 2) (* 0.05 cn7_blkscl))
	dist amplitude
	ang_txt 0
	ang_dir (/ pi 2)
	increm amplitude
  )
  (wtm_malha_escreve)
)

(defun wtm_malha_escreve ()
  (setq e1 (rtos inicio 2 0))
  (setq k1 1)
  (repeat quant
    (cn7_txsimb "r80" "bl" e1 2 "Top_malha_coord" ang_txt)
    (setq psimb_txt (polar psimb_txt ang_dir dist))
    (setq e1 (rtos (+ inicio (* k1 increm)) 2 0))
    (setq k1 (1+ k1))
  );repeat
)



;;;;;;;;;;;;;;;;;;;;;;;;;;;;  Escreve o azimute  ;;;;;;;;;;;;;;;;;;;;;;;;;;;;;;;;;;;;;;;;;;
(defun c:azm ()
  (guarda '("blipmode" "cecolor" "celtype" "clayer" "cmdecho" "orthomode"
          "textstyle" "luprec" "osmode" ))
  (cn7_init)
  (setq grp_type "2")
  (cn7_find_blkscl)
  (setq osmo (getvar "osmode"))
  (setq hakr 0 KR 1)
  (setq zero 0.0)
  (initang)
  (setq escala cn7_blkscl)
  (cn7_verylayer (strcat cn7_prefixlay "Top_azimute") 2)
  (command "._color" "bylayer")
  (setvar "osmode" 33)
  (setq P1 (getpoint "\nPrimeiro ponto:"))
  (while
    (setq P2 (getpoint P1 "\nProximo ponto:"))
     (command P1 P2)
     (setq No (cadr P1))
     (setq Eo (car P1))
     (setq Nf (cadr P2))
     (setq Ef (car P2))
     (setq delta_e (- Ef Eo))
     (setq delta_n (- Nf No))
     (if (= delta_n zero)
       (setq AA "0.0000")
     )
     (if (/= delta_n zero)
       (progn
	 (setq angrad (/ delta_e delta_n))
	 (setq AA (angtos (atan angrad) 0 4))
       )
     )
     (setq angreal (distof AA 2))
     (if (and (>= delta_e zero) (>= delta_n zero))
           ;; 1o Quadrante
       (progn
	 (setq angreal (- 90 angreal))
	 (setq grau (fix angreal))
	 (setq temp (* 60 (- angreal grau)))
	 (setq minuto (fix temp))
	 (setq temp (* 60 (- temp minuto)))
	 (setq grau (rtos grau 2 0))
	 (setq minuto (rtos minuto 2 0))
	 (setq segundo (rtos temp 2 0))
	 (setq quadrante 1)
	  (setq AA (strcat "-> Az=" grau "%%D" minuto "'" segundo "\""))
     (resetang)
     (setq BB (angle P1 P2)
	   DS (distance P1 P2)
	   DS (/ DS KR)
	   P3 (polar P1 BB (/ DS 2.0))
	   P1 P2
     )
     (setq angulo BB)
     (if (or (= quadrante 3) (= quadrante 4))
       (setq angulo (+ angulo PI))
     )
       )
       (if (and (>= delta_e zero) (<= delta_n zero))
	 ;; 2o Quadrante
	 (progn
	   (setq angreal (- 270 angreal))
	   (setq grau (fix angreal))
	   (setq temp (* 60 (- angreal grau)))
	   (setq minuto (fix temp))
	   (setq temp (* 60 (- temp minuto)))
	   (setq grau (rtos grau 2 0))
	   (setq minuto (rtos minuto 2 0))
	   (setq segundo (rtos temp 2 0))
	   (setq quadrante 2)
	    (setq AA (strcat "-> Az=" grau "%%D" minuto "'" segundo "\""))
     (resetang)
     (setq BB (angle P1 P2)
	   DS (distance P1 P2)
	   DS (/ DS KR)
	   P3 (polar P1 BB (/ DS 2.0))
	   P1 P2
     )
     (setq angulo BB)
     (if (or (= quadrante 3) (= quadrante 4))
       (setq angulo (+ angulo PI))
     )
	 )
	 (if (and (<= delta_e zero) (<= delta_n zero))
	   ;; 3o Quadrante
	   (progn
	     (setq angreal (- 270 angreal))
	     (setq grau (fix angreal))
	     (setq temp (* 60 (- angreal grau)))	     (setq minuto (fix temp))
	     (setq temp (* 60 (- temp minuto)))
	     (setq grau (rtos grau 2 0))
	     (setq minuto (rtos minuto 2 0))
	     (setq segundo (rtos temp 2 0))
	     (setq quadrante 3)
	      (setq AA (strcat "<- Az=" grau "%%D" minuto "'" segundo "\""))
     (resetang)
     (setq BB (angle P1 P2)
	   DS (distance P1 P2)
	   DS (/ DS KR)
	   P3 (polar P1 BB (/ DS 2.0))
	   P1 P2
     )
     (setq angulo BB)
     (if (or (= quadrante 3) (= quadrante 4))
       (setq angulo (+ angulo PI))
     )
	   )
	   (if (and (<= delta_e zero) (>= delta_n zero))
	     ;; 4o Quadrante
	     (progn
	       (setq angreal (- 450 angreal))
	       (setq grau (fix angreal))
	       (setq temp (* 60 (- angreal grau)))
	       (setq minuto (fix temp))
	       (setq temp (* 60 (- temp minuto)))
	       (setq grau (rtos grau 2 0))
	       (setq minuto (rtos minuto 2 0))
	       (setq segundo (rtos temp 2 0))
	       (setq quadrante 4)
	        (setq AA (strcat "<- Az=" grau "%%D" minuto "'" segundo "\""))
     (resetang)
     (setq BB (angle P1 P2)
	   DS (distance P1 P2)
	   DS (/ DS KR)
	   P3 (polar P1 BB (/ DS 2.0))
	   P1 P2
     )
     (setq angulo BB)
     (if (or (= quadrante 3) (= quadrante 4))
       (setq angulo (+ angulo PI))
     )
	     )
	   )	 )
       )
     )
     (setvar "osmode" 0)
     (setq psimb_txt (polar P3 (rem (+ BB (/ PI 2.0)) (* PI 2.0)) (* 0.2 escala)))
     (cn7_txsimb "r80" "m" (rtos DS 2 3) 2 "Top_azimute" (rtd angulo))
     (setq psimb_txt (polar P3 (rem (+ BB (* PI 1.5)) (* PI 2.0)) (* 0.2 escala)))
     (cn7_txsimb "r80" "m" AA 2 "Top_azimute" (rtd angulo))
     (setvar "osmode" 33)
     (initang)
  )
  (resetang)
  (setvar "osmode" osmo)
  (devolve)
  (princ)
)

(defun initang ()
  (setvar "ANGBASE" (/ pi 2))
  (setvar "ANGDIR" 1)
  (setvar "AUNITS" 1)			; grau,minuto,segundo
  (setvar "AUPREC" 5)			; 
  (setvar "LUNITS" 2)			; decimal
  (setvar "LUPREC" 4)
)
;;;;;;;;;;;;;;;;;;;;;;;;;;;;;;;;;;;;;;;;;;;;;;;;;;;;;;;;;;;;;;;;;;;;;;;;;;;;;;;;;;;;;;

(defun resetang	()
  (setvar "ANGBASE" 0.0)
  (setvar "ANGDIR" 0)
  (setvar "AUNITS" 1)
  (setvar "AUPREC" 5)
  (setvar "LUNITS" 2)
  (setvar "LUPREC" 4)
)


;funções auxiliares
(defun frac (x)
  (- x (fix x))
)

(defun dtr (a)
  (* pi (/ a 180.0))
)

(defun rtd (a)
  (/ (* a 180.0) pi))



;****************************************************************
;         Interpolacao Topografica
;         Para Confeccao de Curvas de Niveis
;****************************************************************

;***********  Interpolação de 1 curva no meio de outras duas   *************
(defun c:it1 ()
  (setq osmo (getvar "osmode"))
  (setq laymo (getvar "clayer"))
  (cn7_verylayer "Top_curvas_interpoladas" 1)
  (setvar "osmode" 512)
  (setq pt1 (getpoint "\nPrimeiro ponto..."))
  (setq next_pto (getpoint pt1 "\nPróximo ponto..."))
  (setq pt0 (polar pt1 (angle pt1 next_pto) (/ (distance pt1 next_pto) 2)))
  (command "._pline" "_non" pt0)
  (keep)
  (decide)
  (princ)
)


(defun keep ()
	(while (/= nil (setq pt1 (getpoint "\nPrimeiro ponto...")))
	    (progn
  		(setq next_pto (getpoint pt1 "\nPróximo ponto..."))
  		(setq pt0 (polar pt1 (angle pt1 next_pto) (/ (distance pt1 next_pto) 2)))
	  	(command "_non" pt0)
	    );progn
	);while
  	(decide)
);defun


(defun decide ()
  (initget 1 "Undo eXit Continue")
  (setq resp (getkword "\neXit/Undo/Continue <X/U/C>: "))
  (if (= "EXIT" (strcase resp))
    (progn
      (command "")
      (setvar "osmode" osmo)
      (setvar "clayer" laymo)
      (command "._cmdecho" 0)
      (devolve)
      (exit)
      )
    (progn
      (if (= "UNDO" (strcase resp))
	(progn
	  (command "_u")
	  (keep)
	  )
	(keep)
      )
    )
  )
)


;***********  Interpolação de n curvas no meio de outras duas   *************
(defun c:curvas () (setq n_curv (1+ (getint "\nNúmero de curvas a interpolar..."))) (princ))

(defun c:itn ()
  	(if (= nil n_curv) (setq n_curv (1+ (getint "\nNúmero de curvas a interpolar..."))))
  	(setq osmo (getvar "osmode"))
  	(setq laymo (getvar "osmode"))
  	(cn7_verylayer "Top_curvas_interpoladas" 1)
  	(setvar "osmode" 512)
  	(while (/= nil (setq pt1 (getpoint "\nPrimeiro ponto...<ENTER> para terminar...")))
	  (setq next_pto (getpoint pt1 "\nPróximo ponto..."))
	  (command "._line" pt1 next_pto "")
	  (setq e1 (entlast))
	  (command "._divide" (entlast) n_curv "._erase" e1 "")
	)
  	(setvar "osmode" osmo)
  	(setvar "clayer" laymo)
  (princ)
)


;*****************************************************
;gerar taludes
;*****************************************************
(defun C:TALUDE	(/ Qj)
  (guarda '("blipmode" "cecolor" "celtype" "clayer" "cmdecho" "orthomode"
          "textstyle" "luprec" "osmode" ))
  (cn7_init)
  (cn7_verylayer "Top_talude" 1)
  (setvar "osmode" 0)
  (PRINC
    "\nTipo do talude (R/L/E/A): Rocha sã/rocha aLterada/Escavação/<Aterro>: "
  )
  (SETQ Qj (STRCASE (GETSTRING)))
  (IF (= Qj "")
    (SETQ Qj "A")
  )
  (COND	((= Qj "A") (Q@ "ATERRO"))
	((= Qj "R") (Q@ "ROCHAS"))
	((= Qj "L") (Q@ "ROCHAL"))
	((= Qj "E") (Q@ "ESCAVA"))
	(T (PRINC "\Erro na informação do tipo!"))
  )
  (devolve)
  (PRINC)
)

(DEFUN Q@ (QQ	/    Ql	  Q&   Q1   Q#	 Q0   Q$   QO	Q|   Q%	  Q?j
	   Qjj	Q@j  QQj  Qlj  Q&j  Q1j	 Q#j  Q0j  Q$j	QOj  Q|j  Q%j
	   Q?@	Qj@  Q@@  QQ@  Ql@  Q&@	 Q1@  Q#@
	  )
  (DEFUN Q0@ ()
    (DEFUN Q$@ (QO@) (= (/ (FIX QO@) 2) (/ QO@ 2.0)))
    (COMMAND "._ucs"
	     "_e"
	     Q#@
	     "._line"
	     Q&j
	     Q1j
	     ""
	     "._extend"
	     Q@@
	     ""
	     (LIST (SETQ Ql (ENTLAST)) Q1j)
	     ""
    )
    (SETQ Q& (TRANS (CDR (ASSOC 11 (ENTGET Ql))) 0 1))
    (IF	(AND (/= QQ "ATERRO") (NOT (EQUAL Q1j Q& (* QOj Q?@))))
      (PROGN (SETQ Q1  (POLAR Q& (/ PI -2) (* Q?@ (* 0.5 QOj)))
		   Q#  (POLAR Q& (/ PI -2) (* Q?@ QOj))
		   Q@j (/ Q?@ (ABS Q?@))
		   Q?j (+ (ATAN 0.5) (* Q@j (/ PI 2)))
		   Qjj (+ (- (ATAN 0.5)) (* Q@j (/ PI 2)))
		   Q0  (POLAR Q# Q?j (ABS (* Q?@ (* 2 QOj))))
		   QO  (POLAR Q# Qjj (ABS (* Q?@ (* 2 QOj))))
	     )
	     (command "._line" Q0 Q# "")
	     (SETQ Q% (ENTLAST))
	     (command "._line"
		      QO
		      Q#
		      ""
		      "._trim"
		      (SETQ QQj (ENTLAST))
		      Q@@
		      ""
		      (LIST Ql Q1)
		      (LIST Q% Q0)
		      (LIST QQj QO)
		      ""
	     )
	     (SETQ Q$ (TRANS (CDR (ASSOC 10 (ENTGET Q%))) 0 1))
	     (SETQ Q| (TRANS (CDR (ASSOC 10 (ENTGET QQj))) 0 1))
	     (IF (EQUAL Q0 Q$ 1e-6)
	       (PROGN (PRINC "\nAjustando angulo ")
		      (PRINC Q1@)
		      (SETQ Q?j	(+ (ATAN 0.2) (* Q@j (/ PI 2)))
			    Q0	(POLAR Q# Q?j (ABS (* Q?@ (* 2 QOj))))
		      )
		      (COMMAND "._erase"
			       Q%
			       ""
			       "._line"
			       Q0
			       Q#
			       ""
			       "._trim"
			       Q@@
			       ""
			       (LIST (SETQ Q% (ENTLAST)) Q0)
			       ""
		      )
		      (SETQ Q0 (TRANS (CDR (ASSOC 10 (ENTGET Q%))) 0 1))
	       )
	       (SETQ Q0 Q$)
	     )
	     (IF (EQUAL QO Q| 1e-6)
	       (PROGN (PRINC " Ajustando angulo ")
		      (PRINC Q1@)
		      (SETQ Qjj	(+ (- (ATAN 0.2)) (* Q@j (/ PI 2)))
			    QO	(POLAR Q# Qjj (ABS (* Q?@ (* 2 QOj))))
		      )
		      (COMMAND "._erase"
			       QQj
			       ""
			       "._line"
			       QO
			       Q#
			       ""
			       "._trim"
			       Q@@
			       ""
			       (LIST (SETQ QQj (ENTLAST)) QO)
			       ""
		      )
		      (SETQ QO (TRANS (CDR (ASSOC 10 (ENTGET QQj))) 0 1))
	       )
	       (SETQ QO Q|)
	     )
	     (IF (OR (= QQ "ROCHAS") (AND (= QQ "ROCHAL") (Q$@ Q1@)))
	       (COMMAND "._erase" Q% "" "._solid" Q0 QO Q# "" "")
	     )
      )
    )
    (IF	(Q$@ Q1@)
      (PROGN (SETQ Qlj (LIST 0 (/ (CADR Q&) 2)))
	     (command "._line" (POLAR Qlj 0 -1) (POLAR Qlj 0 1) "")
	     (IF (= QQ "ATERRO")
	       (COMMAND "._trim" (ENTLAST) "" (LIST Ql Q&) "")
	       (IF (NOT (EQUAL Q1j Q& (ABS (* Q?@ 2 QOj))))
		 (COMMAND "._trim" (ENTLAST) "" (LIST Ql (quote (0 0))) "")
	       )
	     )
	     (COMMAND "._erase" (ENTLAST) "")
      )
    )
  )
  (DEFUN Q|@ ()
    (SETQ Q&j (quote (0 0 0))
	  Q1j (POLAR Q&j (* (/ Q?@ (ABS Q?@)) (/ PI 2)) 0.001)
    )
    (command "._line" Q&j Q1j "" "._block" Q%j)
    (IF	(TBLSEARCH "BLOCK" Q%j)
      (COMMAND "_y")
    )
    (COMMAND Q&j (ENTLAST) "")
  )
  (SETQ	Q#j (GETVAR "cmdecho")
	Q0j (GETVAR "blipmode")
  )
  (SETVAR "cmdecho" 0)
  (COMMAND "._undo" "_g" "._ucs" "_d"	"ucsatual" "._ucs" "_s" "ucsatual")
  (SETVAR "blipmode" 0)
  (SETQ	QOj 2
	Q|j (* QOj 3)
	QQ  (STRCASE QQ)
	Q%j "$$$ca$$$"
  )
  (IF (NOT Q%@)
    (SETQ Q%@ 1.0)
  )
  (PRINC "\nFator de escala <")
  (PRINC (ABS Q%@))
  (SETQ Q?@ (GETREAL ">: "))
  (IF (NOT Q?@)
    (SETQ Q?@ Q%@)
    (SETQ Q%@ Q?@)
  )
  (IF (= QQ "ATERRO")
    (SETQ Qj@ (ENTSEL "\nLinha de topo do aterro: ")
	  Q@@ (CAR (ENTSEL "\nLinha de saia do aterro: "))
    )
    (SETQ Q@@ (CAR (ENTSEL "\nLinha de topo do corte: "))
	  Qj@ (ENTSEL "\nLinha de pe' do corte: ")
    )
  )
  (IF (AND Q@@ Qj@)
    (PROGN (SETQ QQ@ (CAR Qj@))
	   (Q|@)
	   (COMMAND "._MEASURE" Qj@ "_B" Q%j "_y" (* Q|j (ABS Q?@)))
	   (SETQ Ql@ (SSGET "p")
		 Q&@ (SSLENGTH Ql@)
		 Q1@ 0
	   )
	   (SETQ Q#@ (SSNAME Ql@ 0))
	   (COMMAND "._undo"
		    "_m"
		    "._ucs"
		    "_e"
		    Q#@
		    "._line"
		    Q&j
		    Q1j
		    ""
		    "._extend"
		    Q@@
		    ""
		    (LIST (SETQ Ql (ENTLAST)) Q1j)
		    ""
	   )
	   (SETQ Q& (TRANS (CDR (ASSOC 11 (ENTGET Ql))) 0 1))
	   (IF (EQUAL Q1j Q& 1e-6)
	     (PROGN (PRINC " Invertendo direcao...")
		    (SETQ Q?@ (* -1 Q?@)
			  Q%@ Q?@
		    )
		    (Q|@)
	     )
	   )
	   (COMMAND "._undo" "_b")
	   (REPEAT Q&@	     (SETQ Q#@ (SSNAME Ql@ Q1@))
	     (Q0@)
	     (SETQ Q1@ (1+ Q1@))
	   )
	   (COMMAND "._erase"   Ql@	""	  "._redraw"  "._ucs"
		    "_r"	      "ucsatual"	  "._ucs"	    "_d"
		    "ucsatual"		"._undo"	  "_e"		   )
    )
    (PRINC
      "\nUma ou ambas as linhas de referência não foram definidas!"
    )
  )
  (SETVAR "blipmode" Q0j)
  (SETVAR "cmdecho" Q#j)
  (PRINC)
)

(defun c:pt2 ()
  (cn7_init)
  (setq grp_type "2")
  (cn7_find_blkscl)
  (guarda '("blipmode" "cecolor" "celtype" "clayer" "cmdecho" "orthomode"
          "textstyle" "luprec" "osmode" ))
  (while (/= nil (setq psimb_txt (getpoint "\nMarque um ponto na tela...")))
    (cn7_verylayer "Top_pontos_locados" 2)
    (setq tg_cota (getreal "\nCota desse ponto..."))
    (command "._point" psimb_txt)
    (cn7_txsimb "r80" "bl" (rtos tg_cota 2 2) 2 "Top_pontos_locados" "45")
  )
  (princ)
)



;***********  Interpolação de pontos 2D  *************

(defun c:cvn () (setq desnivel (getreal "\nIntervalo entre as curvas de níveis...")) (princ))

;locação de pontos em 2D
(defun c:ip2 ()
  (if (= nil desnivel) (setq desnivel (getreal "Intervalo entre as curvas...")))
  (setq pt1 (getpoint "\nPrimeiro ponto..."))
  (princ "Selecione seu texto...")
  (setq txt1 (entsel))
  (setq pt2 (getpoint "\nSegundo ponto..."))
  (princ "Selecione seu texto...")
  (setq txt2 (entsel))
  (setq
    pt1_cota (atof (cdr (assoc 1 (entget (car txt1)))))
    pt2_cota (atof (cdr (assoc 1 (entget (car txt2)))))
  )
  (cn7_verylayer "Top_pontos_interpolados" 7)
  (if (< pt1_cota pt2_cota) (ip_crescente) (ip_decrescente))
  (ip_vizinhos)
  (if (> ip_nextmult ip_cota2)  (decide2) (define_pontos))
  (princ)
)

(defun decide2 ()
  	(while (/= nil (setq prox_pto (getpoint "\nPróximo ponto...")))
		(setq pt1 pt2)
	  	(setq txt1 txt2)
	  	(setq pt2 prox_pto)
	  	(princ "\nSelecione o texto respectivo...")
	  	(setq txt2 (entsel))
	  	(setq
		  	pt1_cota (atof (cdr (assoc 1 (entget (car txt1)))))
			pt2_cota (atof (cdr (assoc 1 (entget (car txt2)))))
		)
	  	(if (< pt1_cota pt2_cota) (ip_crescente) (ip_decrescente))
	  	(ip_vizinhos)
	  	(if (>= ip_nextmult ip_cota2) (decide2) (define_pontos))
	)
  	(exit)
  	(princ)
)

  
	  
(defun define_pontos ()
  	(setq n_ptos (1+ (/ (- ip_lastmult ip_nextmult) desnivel)))
  	(setq dt (sqrt (+
			 (expt (- ip_cota2 ip_cota1) 2)
			 (expt (- (nth 0 ip_pt1) (nth 0 ip_pt2)) 2)
			 (expt (- (nth 1 ip_pt1) (nth 1 ip_pt2)) 2)
			)
		 )
	);setq
        (setq dh (- ip_cota2 ip_cota1))
  	(loca_pto)
  	(decide_prox)
)

(defun decide_prox ()
  	(setq next_cota (+ desnivel ip_nextmult))
  	(setq ip_nextmult (+ desnivel ip_nextmult))
  	(if (> next_cota ip_cota2)
	  	(decide2)
	  	(progn
		  (setq dx_pad (/ (* desnivel dt) dh))
		  (setq dx_padp (/ (* dx_pad disth) dt))
  		  (setq pto1 (polar pto1 (angle ip_pt1 ip_pt2) dx_padp))
  		  (command "._point" "_non" pto1)
		)
	 )
    	(decide_prox)
)


(defun loca_pto ()
  	(setq disth (distance ip_pt1 ip_pt2))
  	(setq x (/ (* dt (- ip_nextmult ip_cota1)) dh))
  	(setq xp (/ (* disth x) dt))
  	(setq pto1 (polar ip_pt1 (angle ip_pt1 ip_pt2) xp))
  	(command "._point" "_non" pto1)
)

(defun ip_vizinhos ()
	;  calcula os vizinhos do ponto menor (pt1)
	(setq resto1 (- ip_cota1 (* desnivel (fix (/ ip_cota1 desnivel)))))
  	(setq ip_nextmult (+ ip_cota1 (- desnivel resto1)))
  	(setq resto2 (- ip_cota2 (* desnivel (fix (/ ip_cota2 desnivel)))))
	(setq ip_lastmult (- ip_cota2 resto2))
)
  
(defun ip_crescente ()
  	(setq
	  ip_pt1 pt1
	  ip_cota1 pt1_cota
	  ip_pt2 pt2
	  ip_cota2 pt2_cota
	)
)

(defun ip_decrescente ()
  	(setq
	  ip_pt1 pt2
	  ip_cota1 pt2_cota
	  ip_pt2 pt1
	  ip_cota2 pt1_cota
	)
)

;locação de pontos em 3D
(defun c:pt3 ()
  (cn7_init)
  (setq grp_type "2")
  (cn7_find_blkscl)
  (guarda '("blipmode" "cecolor" "celtype" "clayer" "cmdecho" "orthomode"
          "textstyle" "luprec" "osmode" ))
  (while (/= nil (setq psimb_txt (getpoint "\nMarque um ponto na tela...")))
    (cn7_verylayer "Top_pontos_locados" 2)
    (setq tg_cota (getreal "\nCota desse ponto..."))
    (command "._point" ".xy" psimb_txt tg_cota)
    (cn7_txsimb "r80" "bl" (rtos tg_cota 2 2) 2 "Top_pontos_locados" "45")
  )
  (princ)
)



;*****************************************************************
;Funcao Para Interpolar Pontos 3D
;*****************************************************************

(defun c:ip3 ()
  (if (= nil desnivel) (setq desnivel (getreal "Intervalo entre as curvas...<m>...")))
  (setq incr_z desnivel)
  (setq osmo (getvar "osmode"))
  (setq laymo (getvar "clayer"))
  (setvar "osmode" 8)
  (setq p1 (getpoint "\nEntre com o ponto base..."))
  (setq p2 (getpoint "\nEntre com um segundo ponto..."))
  (cn7_verylayer "Top_pontos_interpolados" 7)
  (setq pbase p2)
  (coord)
  (princ)
)

;********************************************************************
;Funcao coord - separa as cordenadas dos pontos p1 e p2
(defun coord ()
  (setq xp1 (nth 0 p1))
  (setq yp1 (nth 1 p1))
  (setq zp1 (nth 2 p1))
  (setq xp2 (nth 0 p2))
  (setq yp2 (nth 1 p2))
  (setq zp2 (nth 2 p2))
  (verif)
)

;Funcao que verifica se ha interpolacao entre dois pontos escolhidos
(defun verif ()
  (if (< zp2 zp1)
    (progn
      (setq compl (- zp2 (* incr_z (fix (/ zp2 incr_z)))))
      (setq zp3 (+ zp2 (- incr_z compl)))
      (if (<= zp3 zp1)
	(setq resp "t")
	(setq resp "f")
      )
    )
    (progn
      (setq compl (- zp1 (* incr_z (fix (/ zp1 incr_z)))))
      (setq zp3 (+ zp1 (- incr_z compl)))
      (if (>= zp3 zp2)
	(setq resp "f")
	(setq resp "t")
      )
    )
  )
  (if (= resp "t")
    (interpol)
    (goon)
  )
)

;********************************************************************
;Funcao de interpolação dos pontos 
;********************************************************************
(defun interpol ()
  (setq xp3 (+ xp1 (/ (* (- xp2 xp1) (- zp3 zp1)) (- zp2 zp1))))
  (setq yp3 (+ yp1 (/ (* (- yp2 yp1) (- zp3 zp1)) (- zp2 zp1))))
  (setq p3 (list xp3 yp3 zp3))
  (command "._point" "_non" p3)
  (if (< zp1 zp2)
    (setq p1 p3)
    (setq p2 p3)
  )
  (coord)
)

;********************************************************************
;Funcao looping
;********************************************************************(defun goon ()
(defun goon ()
    	(setq p1 pbase)
    	(if (> zp2 zp1) (setq p1 p2))
	(setq p2 (getpoint "\nEntre com o segundo ponto..."))
	(setq pbase p2)
	(coord)
)




;******************************************************************************
; Rotina auxiliar que extrai os dados de uma linha lida *******************
; -> para os programas de locação de pontos a seguir **************************
;******************************************************************************


(defun extrai_n ()
	(setq letra_n (substr linha cont1 1))
	(if (and (/= letra_n " ") (/= letra_n "")(/= letra_n "\t")(/= letra_n ";"))
		(progn
			(setq n_pto (strcat n_pto letra_n))
			(setq cont1 (1+ cont1))
			(extrai_n)
		);progn
	);if
);defun


;************** loca pontos norte-leste **************************************************
(defun cn7_read_file ()
  (setq arq1 (getfiled "Selecione o Arquivo de Dados" (getvar "dwgprefix") "csv;txt;prn" 8))
  (setq arq  (open arq1 "r" "utf8"))
  (setq cont 0)
  (while (/= (read-line arq) nil)
    (setq cont (1+ cont))
  )
  (close arq)
  (cn7_verylayer "Top_pontos_locados" 2)
)


(defun cn7_read_data ()
  (setq cont1 1 n_pto "" cn7_dado1 "" cn7_dado2 "" cn7_dado3 "" cn7_dado4 "" cn7_dado5 "")
  (setq linha (read-line arq))
  (extrai_n)
  (setq cn7_dado1 n_pto n_pto "")
  (while (or (= (substr linha cont1 1) " " ) (= (substr linha cont1 1) "\t")(= (substr linha cont1 1) ";"))
    (setq cont1 (1+ cont1))
  );while
  (extrai_n)
  (setq cn7_dado2 n_pto n_pto "")
  (while (or (= (substr linha cont1 1) " " ) (= (substr linha cont1 1) "\t")(= (substr linha cont1 1) ";"))
    (setq cont1 (1+ cont1))
  );while
  (extrai_n)
  (setq cn7_dado3 n_pto n_pto "")
  (while (or (= (substr linha cont1 1) " " ) (= (substr linha cont1 1) "\t")(= (substr linha cont1 1) ";"))
    (setq cont1 (1+ cont1))
  );while
  (extrai_n)
  (setq cn7_dado4 n_pto n_pto "")
  (while (or (= (substr linha cont1 1) " " ) (= (substr linha cont1 1) "\t")(= (substr linha cont1 1) ";"))
    (setq cont1 (1+ cont1))
  );while
  (extrai_n)
  (setq cn7_dado5 n_pto n_pto "")
  (while (or (= (substr linha cont1 1) " " ) (= (substr linha cont1 1) "\t")(= (substr linha cont1 1) ";"))
    (setq cont1 (1+ cont1))
  );while
)


;locação de pontos extraídos de arquivo
(defun c:tp_loc_ne ()
  (cn7_alert_yes_no
    "Os dados devem estar nesta ordem : "
    "Norte - Leste"
    "Deseja continuar?")
  (if (= alert_resp "no") (exit))
  (guarda '("blipmode" "cecolor" "celtype" "clayer" "cmdecho" "orthomode"
          "textstyle" "luprec" "osmode" ))
  (cn7_read_file)
  (setq arq  (open arq1 "r" "utf8"))
  (repeat cont
    (cn7_read_data)
    (tp_loc_ne_draw)
  );repeat
  (close arq)
  (devolve)
  (princ)
)


(defun tp_loc_ne_draw ()
	(setq loc_pto (list (distof cn7_dado2) (distof cn7_dado1)))
	(command "._point" "_non" loc_pto)
)



;************** loca pontos norte-leste e escreve o nome do ponto *********************************************
(defun c:tp_loc_tne ()
  (cn7_alert_yes_no
    "Os dados devem estar nesta ordem : "
    "Nome - Norte - Leste"
    "Deseja continuar?")
  (if (= alert_resp "no") (exit))
  (guarda '("blipmode" "cecolor" "celtype" "clayer" "cmdecho" "orthomode"
          "textstyle" "luprec" "osmode" ))
  (cn7_read_file)
  (setq arq  (open arq1 "r" "utf8"))
  (repeat cont
    (cn7_read_data)
    (tp_loc_tne_draw)
  );repeat
  (close arq)
  (devolve)
  (princ)
)


(defun tp_loc_tne_draw ()
  (setq loc_pto (list (distof cn7_dado3) (distof cn7_dado2))
	psimb_txt loc_pto)
  (command "._point" loc_pto)
  (cn7_txsimb "r80" "bl" cn7_dado1 2 "Top_pontos_locados" "0")
)

(defun c:tp_loc_topog ()
  (cn7_alert_yes_no
    "Os dados devem estar nesta ordem : "
    "Nome - Norte - Leste - Cota - Observação"
    "Os dois últimos são opcionais. Continuar?")
  (if (= alert_resp "no") (exit))
  (guarda '("blipmode" "cecolor" "celtype" "clayer" "cmdecho" "orthomode"
          "textstyle" "luprec" "osmode" ))
  (setq grp_type "2")
  (cn7_find_blkscl)
  (cn7_read_file)
  (setq arq  (open arq1 "r" "utf8"))
  (repeat cont
    (cn7_read_data)
    (tp_loc_topog_draw)
  );repeat
  (close arq)
  (devolve)
  (princ)
)

(defun tp_loc_topog_draw ()
	(setq y_pto2 (distof cn7_dado2))
	(setq x_pto2 (distof cn7_dado3))
  	(if (= tg_ptloc "2D") (setq z_pto2 0) (setq z_pto2 (distof cn7_dado4)))
	(setq pto_01 (list x_pto2 y_pto2 z_pto2))
	(cn7_verylayer "Top_pontos_locados" 2)
	(command "._insert" (strcat cnp_root "/blocos/tp_loc_topog") "_non"
		 pto_01 cn7_blkscl "" "" cn7_dado1 cn7_dado4 cn7_dado5 cn7_dado2 cn7_dado3)
)



(defun c:tp_loc_sec ()
  (cn7_alert_yes_no
    "Os dados devem estar nesta ordem : "
    "Nome - Norte1 - Leste1 - Norte2 - Leste2"
    "Deseja continuar?")
  (if (= alert_resp "no") (exit))
  (guarda '("blipmode" "cecolor" "celtype" "clayer" "cmdecho" "orthomode"
          "textstyle" "luprec" "osmode" ))
  (setq grp_type "2")
  (cn7_find_blkscl)
  (cn7_read_file)
  (setq arq  (open arq1 "r" "utf8"))
  (repeat cont
    (cn7_read_data)
    (tp_loc_sec_draw)
  );repeat
  (close arq)
  (devolve)
  (princ)
)
;************** 5 colunas - seções **************************************************
;defun

(defun tp_loc_sec_draw ()
  (setq pto_01 (list (distof cn7_dado3) (distof cn7_dado2)))
  (setq pto_02 (list (distof cn7_dado5) (distof cn7_dado4)))
  (setq pto_txt (polar pto_01 (angle pto_01 pto_02) (/ (distance pto_01 pto_02) 2)))
  (setq psimb_txt (polar pto_txt (+ (angle pto_01 pto_02) (/ pi 2)) (* 0.1 cn7_blkscl)))
  (cn7_verylayer "Top_seções_locadas" 4)
  (command "._line" "_non" pto_01 "_non" pto_02 "")
  (cn7_txsimb "r100" "C" cn7_dado1 4 "Top_seções_locadas" (/ (* 180 (angle pto_01 pto_02)) pi))
)

;************* Traçar Perfil Reto ******************************************
(defun pfr_desnivel () (setq desnivel (getreal "\nEntre com o desnível entre as curvas...")))

(defun c:pfr ()
  (if (or
	(= nil pto_inicial)
	(= nil plot_scale2)
	(= nil vt_scale2)
	(= nil hz_scale2)
	(= nil vt_start)
	(= nil hz_start)
	(= nil vt_prof)
	(= nil hz_larg)
	(= nil hz_increm)
	(= nil vt_increm)
      )
    	(progn
	  (alert "
		  Você deve primeiro construir os eixos
	  	  coordenados para executar esse comando.
	  	  Vá em CADNorma -> Aplicativos -> Gráficos -> Eixos para
	  	  Defini-los...
		 "
	  )
	  (exit)
	);progn case T
    );if
  (if (= desnivel nil) (pfr_desnivel))
  (setq pfr_start_pto (getpoint "\nPonto de partida..."))
  (setq pfr_y_start (getreal "\nCota de Partida..."))
  (setq pfr_graf_start (polar pto_inicial (/ pi 2) (* (- pfr_y_start vt_start) (/ (float plot_scale2) (float vt_scale2)))))
  (command "._point" "_non" pfr_graf_start)
  (pfr_decide)
  (pfr_draw_first)
  (setq pfr_last_pto pfr_curr_pto)
  (pfr_keep1)
  (princ)
)

(defun pfr_decide ()
  (initget 1 "Sobe Desce Horizontal Abortar")
  (setq pfr_decision (getkword "\nPróxima direção.. <Sobe/Desce/Horizontal/Abortar> : "))
  (if (= pfr_decision "Abortar") (exit))
)


(defun pfr_draw_first ()
  (setq pfr_next_pto (getpoint "\nSegundo Ponto..."))
  (command "._point" "_non" pfr_next_pto)
  (setq pfr_curr_dist (abs (distance pfr_start_pto pfr_next_pto)))
  (setq pfr_gf_temp1 (polar pfr_graf_start 0 pfr_curr_dist))
  (setq x_curr_pto (nth 0 pfr_gf_temp1))
  (cond
	  ((= pfr_decision "Sobe")
		(setq y_curr_pto (nth 1 (polar pfr_gf_temp1 (/ pi 2) (* desnivel (/ (float plot_scale2) (float vt_scale2)))))))
	  ((= pfr_decision "Desce")		(setq y_curr_pto (nth 1 (polar pfr_gf_temp1 (* 3 (/ pi 2)) (* desnivel (/ (float plot_scale2) (float vt_scale2)))))))
	  ((= pfr_decision "Horizontal")
		(setq y_curr_pto (nth 1 pfr_gf_temp1)))
  );cond
  (setq pfr_curr_pto (list x_curr_pto y_curr_pto))
  (command "._point" "_non" pfr_curr_pto)
)


(defun pfr_keep1 ()
  (while (/= nil (setq pfr_next_pto (getpoint "\nPróximo cruzamento...")))
    	(command "._point" "_non" pfr_next_pto)
  	(setq pfr_curr_dist (abs (distance pfr_start_pto pfr_next_pto)))
  	(setq pfr_gf_temp1 (polar pfr_graf_start 0 pfr_curr_dist))
    	(setq x_curr_pto (nth 0 pfr_gf_temp1))
        (cond
	  ((= pfr_decision "Sobe")
		(setq y_curr_pto (nth 1 (polar pfr_last_pto (/ pi 2) (* desnivel (/ (float plot_scale2) (float vt_scale2)))))))
	  ((= pfr_decision "Desce")
		(setq y_curr_pto (nth 1 (polar pfr_last_pto (* 3 (/ pi 2)) (* desnivel (/ (float plot_scale2) (float vt_scale2)))))))
	  ((= pfr_decision "Horizontal")
		(setq y_curr_pto (nth 1 pfr_last_pto)))
	);cond
    	(setq pfr_curr_pto (list x_curr_pto y_curr_pto))
       	(command "._point" "_non" pfr_curr_pto)
	(setq pfr_last_pto pfr_curr_pto)
  )
  	(pfr_decide)
	(pfr_keep1)
)

;cnp_24

;******************************************************************************
;******************************************************************************
;Aplicativos de Estruturas de Concreto                                         
;******************************************************************************
;******************************************************************************

;Rotina para atualizar tabelas do TQS
(defun c:qs1 ()
  (prompt"\nSelecione a tabela de dados gerada pelo TQS...")
  (setq tqs_fullist (list)
	counter 0
	ent_temp_list (list)
	s1 (ssget '((0 . "TEXT")))
	s1_n (sslength s1)
	tqs_list_selitem nil
	tqs_txtfator (/ (cdr (assoc 40 (entget (ssname s1 0)))) 10.0)
  )
  (command "._undo" "_m")
  (tqs_filterlist)
  (tqs_procesdata)
  (tqs_whatdonext)
)

(defun c:qs2 () (tqs_whatdonext))

;o que fazer com o resultado dos cálculos
(defun tqs_whatdonext ()
  ;constrói a lista para a DCL
  (setq tqs_lista_ferros (list)); "Aço     Diâm. (mm)   Compr(m)   Peso(kg)" ))
  (foreach n tqs_finalist
    (setq linha "")
    (foreach n1 n
      (setq linha (strcat linha "\t" n1))
    )
    (setq tqs_lista_ferros (append tqs_lista_ferros (list linha)))
  )
  ;abre a caixa de diálogo
  (setq dcl_id (load_dialog (strcat cnp_root "/lisp/cadnorma.dcl")))
  (if (not (new_dialog "tqs_somaferro" dcl_id)) (exit))
  (start_list "tqs_ferro_list")
  (mapcar 'add_list tqs_lista_ferros)
  (end_list)
  (action_tile "tqs_ferro_list" "(tqs_ferro_list_action)")
  (if (= nil tqs_list_selitem)
    (progn
      (mode_tile "tqs_ferro_btncomp" 1)
      (mode_tile "tqs_ferro_btnpeso" 1)
    )
    (progn
      (set_tile "tqs_ferro_list" tqs_list_selitem)
      (set_tile "tqs_ferro_txtcomp" tqs_list_selcomp)
      (set_tile "tqs_ferro_txtpeso" tqs_list_selpeso)
    )
  )
  (set_tile "tqs_ferro_60txt" (rtos peso_total_60 2 0))
  (set_tile "tqs_ferro_50txt" (rtos peso_total_50 2 0))
  (action_tile "cancel" "(done_dialog 0)")
  (action_tile "accept" "(done_dialog 1)")
  (action_tile "tqs_ferro_btncomp" "(done_dialog 2)")
  (action_tile "tqs_ferro_btnpeso" "(done_dialog 3)")
  (action_tile "tqs_ferro_60btn" "(done_dialog 4)")
  (action_tile "tqs_ferro_50btn" "(done_dialog 5)")
  (setq tqs_somaferro_dcl (start_dialog))
  (unload_dialog dcl_id)
  (cond
    ((= tqs_somaferro_dcl 2) (tqs_substext 2))
    ((= tqs_somaferro_dcl 3) (tqs_substext 3))
    ((= tqs_somaferro_dcl 4) (tqs_substext 4))
    ((= tqs_somaferro_dcl 5) (tqs_substext 5))
  )
  (princ)
)

;clique no texto para substitui-lo
(defun tqs_substext (tqs_substext_code)
  (cond
    ((= tqs_substext_code 2) (setq new_text tqs_list_selcomp))
    ((= tqs_substext_code 3) (setq new_text tqs_list_selpeso))
    ((= tqs_substext_code 4) (setq new_text (strcat (rtos peso_total_60 2 0) " kg")))
    ((= tqs_substext_code 5) (setq new_text (strcat (rtos peso_total_50 2 0) " kg")))
  )
  (prompt "\nSelecione o texto a substituir...")
  (setq ent (entsel)
	ent_name (car ent)
	ent_list (entget ent_name)
	ent_txlen (strlen (cdr (assoc 1 ent_list)))
	ent_list (entmod (subst (cons 1 new_text) (assoc 1 ent_list) ent_list))
	dif_txt (- ent_txlen (strlen new_text))
  )
;;;  (setq dif_txt (- ent_txlen (strlen new_text)))
  (repeat dif_txt
    (setq new_text (strcat " " new_text)
	  ent_list (entmod (subst (cons 1 new_text) (assoc 1 ent_list) ent_list))
    )
  )
  (setq resp (getstring "\nTecle <ENTER> para retornar ou qualquer tecla para terminar..."))
  (if (= resp "")
    (tqs_whatdonext)
    (exit)
  )
)	

;ao selecionar um item na lista...
(defun tqs_ferro_list_action ()
  (setq tqs_list_selitem $value
	tqs_list_sellist (nth (fix (distof tqs_list_selitem)) tqs_finalist)
	tqs_list_selcomp (nth 2 tqs_list_sellist)
	tqs_list_selpeso (nth 3 tqs_list_sellist)
  )
  (mode_tile "tqs_ferro_btncomp" 0)
  (mode_tile "tqs_ferro_btnpeso" 0)
  (set_tile "tqs_ferro_txtcomp" tqs_list_selcomp)
  (set_tile "tqs_ferro_txtpeso" tqs_list_selpeso)
)

;processa os dados da lista final (tqs_fullist6), separando a soma de todas as ferragens
(defun tqs_procesdata ()
  (setq soma_4 0.0 soma_5 0.0 soma_6 0.0 soma_8 0.0
	soma_10 0.0 soma_12 0.0 soma_16 0.0
	soma_20 0.0 soma_22 0.0 soma_25 0.0 soma_32 0.0 soma_40 0.0
	peso_total_50 0.0 peso_total_60 0.0
  )
  ;analisa a lista total e soma cada bitola
  (foreach n tqs_fullist6
    (setq bitola_ent (nth 2 n)
	  bitola_list (entget bitola_ent)
	  bitola_valor (cdr (assoc 1 bitola_list))
	  total_ent (nth 5 n)
	  total_list (entget total_ent)
	  total_valor (cdr (assoc 1 total_list))
    )
    (cond
      ((= 4.2 (distof bitola_valor)) (setq soma_4 (+ soma_4 (distof total_valor))))
      ((= 5.0 (distof bitola_valor)) (setq soma_5 (+ soma_5 (distof total_valor))))
      ((= 6.3 (distof bitola_valor)) (setq soma_6 (+ soma_6 (distof total_valor))))
      ((= 8.0 (distof bitola_valor)) (setq soma_8 (+ soma_8 (distof total_valor))))
      ((= 10.0 (distof bitola_valor)) (setq soma_10 (+ soma_10 (distof total_valor))))
      ((= 12.5 (distof bitola_valor)) (setq soma_12 (+ soma_12 (distof total_valor))))
      ((= 16.0 (distof bitola_valor)) (setq soma_16 (+ soma_16 (distof total_valor))))
      ((= 20.0 (distof bitola_valor)) (setq soma_20 (+ soma_20 (distof total_valor))))
      ((= 22.0 (distof bitola_valor)) (setq soma_22 (+ soma_22 (distof total_valor))))
      ((= 25.0 (distof bitola_valor)) (setq soma_25 (+ soma_25 (distof total_valor))))
      ((= 32.0 (distof bitola_valor)) (setq soma_32 (+ soma_32 (distof total_valor))))
      ((= 40.0 (distof bitola_valor)) (setq soma_40 (+ soma_40 (distof total_valor))))
    )
  )
  (setq tqs_mensagem "Resumo de Ferragens\n"
	tqs_finalist (list)
  )
  (if (/= 0.0 soma_4)
    (setq peso_total_60 (+ peso_total_60 (* soma_4 0.109))
	  tqs_mensagem (strcat tqs_mensagem "\nFerro 4.2: " (rtos (/ soma_4 100.0) 2 0) "m / " (rtos (* (/ soma_4 100.0) 0.109) 2 0) "kg")
	  tqs_finalist (append tqs_finalist (list (list "60B" "5" (rtos (/ soma_4 100.0) 2 0) (rtos (* (/ soma_4 100.0) 0.109) 2 0))))
    )
  )
  (if (/= 0.0 soma_5)
    (setq peso_total_60 (+ peso_total_60 (* (/ soma_5 100.0) 0.154))
	  tqs_mensagem (strcat tqs_mensagem "\nFerro 5.0: " (rtos (/ soma_5 100.0) 2 0) "m / " (rtos (* (/ soma_5 100.0) 0.154) 2 0) "kg")
	  tqs_finalist (append tqs_finalist (list (list "60B" "5" (rtos (/ soma_5 100.0) 2 0) (rtos (* (/ soma_5 100.0) 0.154) 2 0))))
    )
  )
  (if (/= 0.0 soma_6)
    (setq peso_total_50 (+ peso_total_50 (* (/ soma_6 100.0) 0.245))
	  tqs_mensagem (strcat tqs_mensagem "\nFerro 6.3: " (rtos (/ soma_6 100.0) 2 0) "m / " (rtos (* (/ soma_6 100.0) 0.245) 2 0) "kg")
	  tqs_finalist (append tqs_finalist (list (list "50A" "6.3" (rtos (/ soma_6 100.0) 2 0) (rtos (* (/ soma_6 100.0) 0.245) 2 0))))
    )
  )
  (if (/= 0.0 soma_8)
    (setq peso_total_50 (+ peso_total_50 (* (/ soma_8 100.0) 0.395))
	  tqs_mensagem (strcat tqs_mensagem "\nFerro 8.0: " (rtos (/ soma_8 100.0) 2 0) "m / " (rtos (* (/ soma_8 100.0) 0.395) 2 0) "kg")
	  tqs_finalist (append tqs_finalist (list (list "50A" "8" (rtos (/ soma_8 100.0) 2 0) (rtos (* (/ soma_8 100.0) 0.395) 2 0))))
    )
  )
  (if (/= 0.0 soma_10)
    (setq peso_total_50 (+ peso_total_50 (* (/ soma_10 100.0) 0.617))
	  tqs_mensagem (strcat tqs_mensagem "\nFerro 10.0: " (rtos (/ soma_10 100.0) 2 0) "m / " (rtos (* (/ soma_10 100.0) 0.617) 2 0) "kg")
	  tqs_finalist (append tqs_finalist (list (list "50A" "10" (rtos (/ soma_10 100.0) 2 0) (rtos (* (/ soma_10 100.0) 0.617) 2 0))))
    )
  )
  (if (/= 0.0 soma_12)
    (setq peso_total_50 (+ peso_total_50 (* (/ soma_12 100.0) 0.963))
	  tqs_mensagem (strcat tqs_mensagem "\nFerro 12.5: " (rtos (/ soma_12 100.0) 2 0) "m / " (rtos (* (/ soma_12 100.0) 0.963) 2 0) "kg")
	  tqs_finalist (append tqs_finalist (list (list "50A" "12.5" (rtos (/ soma_12 100.0) 2 0) (rtos (* (/ soma_12 100.0) 0.963) 2 0))))
    )
  )
  (if (/= 0.0 soma_16)
    (setq peso_total_50 (+ peso_total_50 (* (/ soma_16 100.0) 1.578))
	  tqs_mensagem (strcat tqs_mensagem "\nFerro 16.0: " (rtos (/ soma_16 100.0) 2 0) "m / " (rtos (* (/ soma_16 100.0) 1.578) 2 0) "kg")
	  tqs_finalist (append tqs_finalist (list (list "50A" "16" (rtos (/ soma_16 100.0) 2 0) (rtos (* (/ soma_16 100.0) 1.578) 2 0))))
    )
  )
  (if (/= 0.0 soma_20)
    (setq peso_total_50 (+ peso_total_50 (* (/ soma_20 100.0) 2.466))
	  tqs_mensagem (strcat tqs_mensagem "\nFerro 20.0: " (rtos (/ soma_20 100.0) 2 0) "m / " (rtos (* (/ soma_20 100.0) 2.466) 2 0) "kg")
	  tqs_finalist (append tqs_finalist (list (list "50A" "20" (rtos (/ soma_20 100.0) 2 0) (rtos (* (/ soma_20 100.0) 2.466) 2 0))))
    )
  )
  (if (/= 0.0 soma_22)
    (setq peso_total_50 (+ peso_total_50 (* (/ soma_22 100.0) 2.984))
	  tqs_mensagem (strcat tqs_mensagem "\nFerro 22.0: " (rtos (/ soma_22 100.0) 2 0) "m / " (rtos (* (/ soma_22 100.0) 2.984) 2 0) "kg")
	  tqs_finalist (append tqs_finalist (list (list "50A" "22" (rtos (/ soma_22 100.0) 2 0) (rtos (* (/ soma_22 100.0) 2.984) 2 0))))
    )
  )
  (if (/= 0.0 soma_25)
    (setq peso_total_50 (+ peso_total_50 (* (/ soma_25 100.0) 3.853))
	  tqs_mensagem (strcat tqs_mensagem "\nFerro 25.0: " (rtos (/ soma_25 100.0) 2 0) "m / " (rtos (* (/ soma_25 100.0) 3.853) 2 0) "kg")
	  tqs_finalist (append tqs_finalist (list (list "50A" "25" (rtos (/ soma_25 100.0) 2 0) (rtos (* (/ soma_25 100.0) 3.853) 2 0))))
    )
  )
  
  (if (/= 0.0 soma_40)
    (setq peso_total_50 (+ peso_total_50 (* (/ soma_40 100.0) 10.00))
	  tqs_mensagem (strcat tqs_mensagem "\nFerro 40.0: " (rtos (/ soma_40 100.0) 2 0) "m / " (rtos (* (/ soma_40 100.0) 10.00) 2 0) "kg")
	  tqs_finalist (append tqs_finalist (list (list "50A" "40" (rtos (/ soma_40 100.0) 2 0) (rtos (* (/ soma_40 100.0) 10.00) 2 0))))
    )
  )
  ;totaliza os pesos
  (setq tqs_mensagem (strcat tqs_mensagem "\n\nTotal 60A: " (rtos peso_total_60 2 0) "kg")
	tqs_mensagem (strcat tqs_mensagem "\nTotal 50A: " (rtos peso_total_50 2 0) "kg")	
	tqs_mensagem (strcat tqs_mensagem "\n\npor Denio Guimarães\nwww.cadnorma.com.br")
  )
  (alert tqs_mensagem)
  
)

;filtra a lista até encontrar a lista final arrumada
(defun tqs_filterlist ()
  (repeat s1_n
    (setq ent_name (ssname s1 counter)
	  ent_list (entget ent_name)
	  ent_y (nth 1 (cdr (assoc 10 ent_list)))
	  ent_x (nth 0 (cdr (assoc 10 ent_list)))
	  ent_temp_list (append (list ent_y ent_x ent_name) ent_temp_list)
    )
    (setq counter (1+ counter))
    (setq tqs_fullist (append (list ent_temp_list) tqs_fullist)
	  ent_temp_list (list)
    )
  )
  ;a seguinte lista é ordenada ela coordenada Y.
  ;nesta etapa os textos estão alinhados
  (setq tqs_fullist2 (vl-sort tqs_fullist
	   (function (lambda (e1 e2) (> (nth 0 e1) (nth 0 e2))))))
  ;agora é necessário ordenar dentro de cada linha. Para isso será
  ;gerada uma nova lista, contendo cada elemento correspondendo a uma linha (alinhados em Y)
  (setq tqs_fullist3 (list)
	counter 0
	tqs_fullist2_n (length tqs_fullist2)
	y_atual nil
	linha_lista (list)
  )
  (while (/= nil (nth counter tqs_fullist2))
    (setq y_atual (nth 0 (nth counter tqs_fullist2))
	  linha_lista (list y_atual)
    )
    (while
      (and
	(/= (nth counter tqs_fullist2) nil)
	;(= (rtos y_atual 2 0) (rtos (nth 0 (nth counter tqs_fullist2)) 2 0))
	(< (abs (-  y_atual (nth 0 (nth counter tqs_fullist2)))) tqs_txtfator)
      )
      (setq linha_lista (append  linha_lista (list (cdr (nth counter tqs_fullist2))))
	    counter(1+ counter)
      )
    )
    (setq tqs_fullist3 (append (list linha_lista) tqs_fullist3))
  )
  ;agora que separei cada linha, é preciso ordenar por x
  (setq tqs_fullist4 (list))
  (foreach n tqs_fullist3
    (setq x_ordenado (vl-sort (cdr n)
	   (function (lambda (e1 e2) (< (nth 0 e1) (nth 0 e2))))))
    (setq tqs_fullist4 (append (list x_ordenado) tqs_fullist4))
  )
  ;agora pecisa extrair a lista final, contendo apenas os nomes das entidades odenadas
  (setq tqs_fullist5 (list)
	tqs_fullist4_n (length tqs_fullist4)
	linha (list)
	counter 0
  )
  (repeat tqs_fullist4_n
    (setq elem (nth counter tqs_fullist4))
    (foreach n elem
      (setq linha (append linha (list (nth 1 n))))
    )
    (setq tqs_fullist5 (append tqs_fullist5 (list linha))
	  counter (1+ counter)
	  linha (list)
    )
  )
  ;agora elimina as linhas órfãs
  (setq tqs_fullist6 (list))
  (foreach n tqs_fullist5
    (if (= 6 (length n))
      (setq tqs_fullist6 (append tqs_fullist6 (list n)))
    )
  )
)

;cnp_31

;******************************************************************************
;******************************************************************************
;QuantNorma
;******************************************************************************
;******************************************************************************
;programa de levantamento de quantidades em desenhos 
;iniciado em 16/04/2010

;************************************************************
;definição do prefixo de rede  ******************************
;************************************************************
(setq cnqt_prefix "cnqt");cnp_user)
;;;(setq file (open (strcat cnp_netroot "/net_libname.txt") "r"))
;;;(setq cnqt_prefix (read-line file))
;;;(close file)

;função principal
(defun c:qn ()
  (cnqt)
)

;função principal - abre a DCL para inserção de símbolos
(defun cnqt ()
  (cnqt_start_readfile)
  (setq cnqt_familist nil)
  ;lê as famíias existentes
  (setq open_file (open (strcat cnp_netroot "/quant/familias.txt") "r" "utf8"))
  (while (/= nil (setq linha (read-line open_file)))
    (setq cnqt_familist (append cnqt_familist (list linha)))
  )
  (close open_file)
  (setq dcl_id (load_dialog (strcat cnp_root "/lisp/cadnorma.dcl")))
  (if (not (new_dialog "cn9_quant" dcl_id)) (exit))
  (start_list "cnqt_familia")
  (mapcar 'add_list cnqt_familist)
  (end_list)
  (set_tile "cnqt_familia" (rtos (fix (distof cnqt_familia)) 2 0))
  (action_tile "cnqt_familia" "(cnqt_familia_update)")
  (cnqt_updall)
  (action_tile "cnqt_group" "(cnqt_updsub)")
  (action_tile "cnqt_subgroup" "(cnqt_updlist)")
  (action_tile "cnqt_list" "(cnqt_selist)")
  (action_tile "cancel" "(done_dialog 0)")
  (action_tile "accept" "(done_dialog 1)")
  (action_tile "cnqt_grp_new" "(done_dialog 2)")
  (action_tile "cnqt_grp_rename" "(done_dialog 3)")
  (action_tile "cnqt_sub_new" "(done_dialog 4)")
  (action_tile "cnqt_sub_rename" "(done_dialog 5)")
  (action_tile "cnqt_button_edit" "(done_dialog 6)")
  (action_tile "cnqt_button_new" "(done_dialog 7)")
  (action_tile "cnqt_codify" "(done_dialog 8)")
  (action_tile "cnqt_change" "(done_dialog 9)")
  (setq cnquant_dialog (start_dialog))
  (unload_dialog dcl_id)
  (if (= 1 cnquant_dialog) (cnqt_ok))
  (if (= 2 cnquant_dialog) (cnqt_grp_new))
  (if (= 3 cnquant_dialog) (cnqt_grp_rename))
  (if (= 4 cnquant_dialog) (cnqt_sub_new))
  (if (= 5 cnquant_dialog) (cnqt_sub_rename))
  (if (= 6 cnquant_dialog) (cnqt_item_edit))
  (if (= 7 cnquant_dialog) (cnqt_item_new))
  (if (= 8 cnquant_dialog) (cnqt_codify))
  (if (= 9 cnquant_dialog) (cnqt_change))
)

;decide o tipo de seleção a ser utilizado
(defun cnqt_codify ()
  (cnqt_write_lastcode)
  (setq attdia_mode (getvar "attdia"))
  (setvar "attdia" 0)
  (cond
    ((= item_type "1") (cnqt_codify_unit))
    ((= item_type "2") (cnqt_codify_linear))
    ((= item_type "3") (cnqt_codify_area))
    ((= item_type "4") (cnqt_codify_volume))
  )
  (setvar "attdia" attdia_mode)
)

;botão ok
(defun cnqt_ok ()
  (if (= nil cnqt_code)
    (progn
      (alert "Nenhum código selecionado!")
      (exit)
    )
    (progn
      (cnqt_write_lastcode)
      (setq cnqt_dcl_btnedit 0)
      (setq cnqt_itemnew_dialog 0)
    )
  )
)


;ao selecionar uma nova família
(defun cnqt_familia_update ()
  (setq cnqt_familia_n $value)
   (if (< (fix (distof cnqt_familia_n)) 10)
    (setq cnqt_familia (strcat "0" cnqt_familia_n))
    (setq cnqt_familia cnqt_familia_n)
  )
  (setq cnqt_grp "00"
	cnqt_sub "00"
	cnqt_selitem "0"
	cnqt_code (strcat cnqt_prefix cnqt_familia cnqt_grp cnqt_sub cnqt_selitem))
  (cnqt_updall)
)


;escreve o último código selecionado
(defun cnqt_write_lastcode ()
  (setq open_file (open (strcat cnp_root "/quant/last_code.txt") "w" "utf8"))
  (setq cnqt_code (strcat cnqt_prefix cnqt_familia cnqt_grp cnqt_sub cnqt_selitem))
  (write-line cnqt_code open_file)
  (close open_file)
)

;botão "Novo" para Item
(defun cnqt_item_new ()
  (setq cnqt_currfile (strcat cnp_netroot "/quant/" cnqt_prefix cnqt_familia cnqt_grp cnqt_sub ".txt"))
  (setq list_len (length cnqt_sublist_descr)
	item_sufix (rtos (1+ list_len) 2 0))
  (setq new_item_text (strcat "Item " item_sufix))
  (setq new_item_custo "1.00")
  (setq new_item_type "1")
  (setq item_lista nil)
  ;abre e gerencia a caixa de diálogo do nome do novo subgrupo
  (setq dcl_id (load_dialog (strcat cnp_root "/lisp/cadnorma.dcl")))
  (if (not (new_dialog "cnqt_edit_item" dcl_id)) (exit))
  (set_tile "cnqt_edit_label" "Adicionando Item")
  (set_tile "cnqt_edit_newtext" new_item_text)
  (set_tile "cnqt_edit_type" new_item_type)
  (set_tile "cnqt_edit_newcusto" new_item_custo)
  (action_tile "cnqt_edit_newtext" "(setq new_item_text $value)")
  (action_tile "cnqt_edit_newcusto" "(setq new_item_custo $value)")
  (action_tile "cnqt_edit_type" "(setq new_item_type $value)")
  (action_tile "accept" "(done_dialog 1)")
  (mode_tile "cnqt_edit_newtext" 2)
  (setq cnqt_itemnew_dialog (start_dialog))
  (unload_dialog dcl_id)
  (if (= 1 cnqt_itemnew_dialog)
    (progn
      (setq open_file (open cnqt_currfile "r" "utf8"))
      (while (/= nil (setq linha (read-line open_file)))
	(cnqt_separa_dados)
	(setq item_lista (append item_lista (list (list item_type item_custo item_text))))
      )
      (close open_file)
      (setq open_file (open (strcat cnp_netroot "/quant/" cnqt_prefix cnqt_familia cnqt_grp cnqt_sub ".txt") "w" "utf8"))
      (foreach n item_lista
	(write-line (strcat (nth 0 n) ";" (nth 1 n) ";" (nth 2 n)) open_file)
      )
      (write-line (strcat new_item_type ";" new_item_custo ";" new_item_text) open_file)
      (close open_file)
      (q_update_data)
    );progn
  )
  (cnqt_start_readfile)
  (cnqt)
)

;botão "editar" para item selecionado
(defun cnqt_item_edit ()
  ;(cnqt_write_lastcode)
  (setq cnqt_currfile (strcat cnp_netroot "/quant/" cnqt_prefix cnqt_familia cnqt_grp cnqt_sub ".txt"))
  (setq open_file (open cnqt_currfile "r" "utf8"))
  (setq cnqt_new_itemlist nil item_lista nil)
  (while (/= nil (setq linha (read-line open_file)))
    (cnqt_separa_dados)
    (setq item_lista (append item_lista (list (list item_type item_custo item_text))))
  )
  (close open_file)
  ;(setq cnqt_item (nth (fix (distof cnqt_selitem)) cnqt_sublist_descr))
  (setq item_type (nth 0 (nth (fix (distof cnqt_selitem)) item_lista))
	item_custo (nth 1 (nth (fix (distof cnqt_selitem)) item_lista))
	item_text (nth 2 (nth (fix (distof cnqt_selitem)) item_lista))
  )
  (setq dcl_id (load_dialog (strcat cnp_root "/lisp/cadnorma.dcl")))
  (if (not (new_dialog "cnqt_edit_item" dcl_id)) (exit))
  (setq cnqt_editem_newtype item_type)
  (setq cnqt_editem_newcusto item_custo)
  (setq cnqt_editem_newtext item_text)
  (set_tile "cnqt_edit_label" "Editando Item")
  (set_tile "cnqt_edit_newtext" item_text)
  (set_tile "cnqt_edit_newcusto" item_custo)
  (set_tile "cnqt_edit_type" item_type)
  (action_tile "cnqt_edit_newtext" "(setq cnqt_editem_newtext $value)")
  (action_tile "cnqt_edit_newcusto" "(setq cnqt_editem_newcusto $value)")
  (action_tile "cnqt_edit_type" "(setq cnqt_editem_newtype $value)")
  (action_tile "accept" "(done_dialog 1)")
  (action_tile "cancel" "(done_dialog 0)")
  (mode_tile "cnqt_edit_newtext" 2)
  (setq cnqt_dcl_btnedit (start_dialog))
  (unload_dialog dcl_id)
  (if (= 1 cnqt_dcl_btnedit)
    (progn
      (setq counter 0
	    cnqt_new_itemlist nil
	    cnqt_new_custolist nil)
      (repeat (length item_lista)
	(setq n (nth counter item_lista))
	(if (= counter (fix (distof cnqt_selitem)))
	  (progn
	    (setq cnqt_new_itemlist (append cnqt_new_itemlist (list (list cnqt_editem_newtype cnqt_editem_newcusto cnqt_editem_newtext))))
	    (setq counter (1+ counter))
	  )
	  (progn
	    (setq cnqt_new_itemlist (append cnqt_new_itemlist (list (nth counter item_lista))))
	    (setq counter (1+ counter))
	  )
	)
      )
      (setq open_file (open (strcat cnp_netroot "/quant/" cnqt_prefix cnqt_familia cnqt_grp cnqt_sub ".txt") "w" "utf8"))
      (setq cnqt_currfile (strcat cnp_netroot "/quant/" cnqt_prefix cnqt_familia cnqt_grp cnqt_sub ".txt"))
      (foreach n cnqt_new_itemlist
	(write-line (strcat (nth 0 n) ";" (nth 1 n) ";" (nth 2 n)) open_file)
      )
      (close open_file)
      (q_update_data)
    );progn
  )
  (cnqt_start_readfile)
  (cnqt)

)

;botão "Renomear" para subgrupos
(defun cnqt_sub_rename ()
  (cnqt_write_lastcode)
  (setq cnqt_subname (nth (fix (distof cnqt_sub)) cnqt_sublist))
  (setq dcl_id (load_dialog (strcat cnp_root "/lisp/cadnorma.dcl")))
  (if (not (new_dialog "cnqt_edit" dcl_id)) (exit))
  (setq cnqt_subname_new cnqt_subname)
  (set_tile "cnqt_edit_label" "Renomeando Subgrupo")
  (set_tile "cnqt_edit_newtext" cnqt_subname)
  (mode_tile "cnqt_edit_newtext" 2)
  (action_tile "cnqt_edit_newtext" "(setq cnqt_subname_new $value)")
  (action_tile "accept" "(done_dialog 1)")
  (setq cnqt_dcl_rename (start_dialog))
  (unload_dialog dcl_id)
;  (if (= 0 cnqt_dcl_rename) (exit))
  (if (= 1 cnqt_dcl_rename)
    (progn
      (setq counter 0
	    cnqt_new_sublist nil)
      (repeat (length cnqt_sublist)
	(setq n (nth counter cnqt_sublist))
	(if (= counter (fix (distof cnqt_sub)))
	  (progn
	    (setq cnqt_new_sublist (append cnqt_new_sublist (list cnqt_subname_new)))
	    (setq counter (1+ counter))
	  )
	  (progn
	    (setq cnqt_new_sublist (append cnqt_new_sublist (list (nth counter cnqt_sublist))))
	    (setq counter (1+ counter))
	  )
	)
      )
      (setq open_file (open (strcat cnp_netroot "/quant/" cnqt_prefix cnqt_familia cnqt_grp ".txt") "w" "utf8"))
      (foreach n cnqt_new_sublist
	(write-line n open_file)
      )
      (close open_file)
      (q_update_data)
    )
  );if
  (cnqt_start_readfile)
  (cnqt)
)


;botão "Novo" para subgrupos
(defun cnqt_sub_new ()
  ;(cnqt_write_lastcode)
  (setq open_file_list nil)
  ;conta subgrupos existentes e determina nome do próximo
  (setq open_file (open (strcat cnp_netroot "/quant/" cnqt_prefix cnqt_familia cnqt_grp ".txt") "r" "utf8")
	    counter 0)
  (while (/= nil (setq linha (read-line open_file)))
    (setq open_file_list (append open_file_list (list linha)))
    (setq counter (1+ counter))
  )
  (close open_file)
  (if (< counter 10)
    (setq new_sub_code (strcat "0" (rtos counter 2 0)))
    (setq new_sub_code (rtos counter 2 0))
  )
  (setq new_sub_name (strcat "Subgrupo " new_sub_code))
  ;abre e gerencia a caixa de diálogo do nome do novo subgrupo
  (setq dcl_id (load_dialog (strcat cnp_root "/lisp/cadnorma.dcl")))
  (if (not (new_dialog "cnqt_edit" dcl_id)) (exit))
  (set_tile "cnqt_edit_newtext" new_sub_name)
  (mode_tile "cnqt_edit_newtext" 2)
  (action_tile "cnqt_edit_newtext" "(setq new_sub_name $value)")
  (action_tile "accept" "(done_dialog 1)")
  (setq cnqt_subnew_dialog (start_dialog))
  (unload_dialog dcl_id)
  (if (= 1 cnqt_subnew_dialog)
    (progn
      (setq open_file (open (strcat cnp_netroot "/quant/" cnqt_prefix cnqt_familia cnqt_grp ".txt") "w" "utf8"))
      (foreach n open_file_list
	(write-line n open_file)
      )
      (write-line new_sub_name open_file)
      (close open_file)
      ;cria o arquivo-lista do primeiro subgrupo
      (setq open_file (open (strcat cnp_netroot "/quant/" cnqt_prefix cnqt_familia cnqt_grp new_sub_code ".txt") "w" "utf8"))
      (write-line "1;1.00;item 01" open_file)
      (close open_file)
      (q_update_data)
    );progn
  )
  (cnqt_write_lastcode)
  (cnqt_start_readfile)
  (cnqt)
)

;botão Rename para grupos
(defun cnqt_grp_rename ()
  (cnqt_write_lastcode)
  (setq cnqt_grpname (nth (fix (distof cnqt_grp)) cnqt_grplist))
  (setq dcl_id (load_dialog (strcat cnp_root "/lisp/cadnorma.dcl")))
  (if (not (new_dialog "cnqt_edit" dcl_id)) (exit))
  (setq cnqt_grpname_new cnqt_grpname)
  (set_tile "cnqt_edit_label" "Renomeando Grupo")
  (set_tile "cnqt_edit_newtext" cnqt_grpname)
  (mode_tile "cnqt_edit_newtext" 2)
  (action_tile "cnqt_edit_newtext" "(setq cnqt_grpname_new $value)")
  (action_tile "accept" "(done_dialog 1)")
  (action_tile "cancel" "(done_dialog 0)")
  (setq cnqt_dcl_rename (start_dialog))
  (unload_dialog dcl_id)
;  (if (= 0 cnqt_dcl_rename) (exit))
  (if (= 1 cnqt_dcl_rename)
    (progn
      (setq counter 0
	    cnqt_new_grplist nil)
      (repeat (length cnqt_grplist)
	(setq n (nth counter cnqt_grplist))
	(if (= counter (fix (distof cnqt_grp)))
	  (progn
	    (setq cnqt_new_grplist (append cnqt_new_grplist (list cnqt_grpname_new)))
	    (setq counter (1+ counter))
	  )
	  (progn
	    (setq cnqt_new_grplist (append cnqt_new_grplist (list (nth counter cnqt_grplist))))
	    (setq counter (1+ counter))
	  )
	)
      )
      (setq open_file (open (strcat cnp_netroot "/quant/" cnqt_prefix cnqt_familia ".txt") "w" "utf8"))
      (foreach n cnqt_new_grplist
	(write-line n open_file)
      )
      (close open_file)
      (q_update_data)
    )
  );if
  (cnqt_start_readfile)
  (cnqt)
)

;botão "Novo" para Grupo
(defun cnqt_grp_new ()
  (cnqt_write_lastcode);teste
  (setq open_file_list nil)
  ;conta grupos existentes e determina nome do próximo
  (setq open_file (open (strcat cnp_netroot "/quant/" cnqt_prefix cnqt_familia ".txt") "r" "utf8")
	    counter 0)
  (while (/= nil (setq linha (read-line open_file)))
    (setq open_file_list (append open_file_list (list linha)))
    (setq counter (1+ counter))
  )
  (close open_file)
  (if (< counter 10);(= 1 (strlen (rtos counter 2 0)))
    (setq new_grp_code (strcat "0" (rtos counter 2 0)))
    (setq new_grp_code (rtos counter 2 0))
  )
  (setq new_grp_name (strcat "Grupo " new_grp_code))
  ;abre e gerencia ca caixa de diálogo do nome do novo grupo
  (setq dcl_id (load_dialog (strcat cnp_root "/lisp/cadnorma.dcl")))
  (if (not (new_dialog "cnqt_edit" dcl_id)) (exit))
  (set_tile "cnqt_edit_label" "Criando novo Grupo")
  (set_tile "cnqt_edit_newtext" new_grp_name)
  (mode_tile "cnqt_edit_newtext" 2)
  (action_tile "cnqt_edit_newtext" "(setq new_grp_name $value)")
  (action_tile "accept" "(done_dialog 1)")
  (action_tile "cancel" "(done_dialog 0)")
  (setq cnqt_grpnew_dialog (start_dialog))
  (unload_dialog dcl_id)
;  (if (= 0 cnqt_grpnew_dialog) (exit))
  (if (= 1 cnqt_grpnew_dialog)
    (progn
      (setq open_file (open (strcat cnp_netroot "/quant/" cnqt_prefix cnqt_familia ".txt") "w" "utf8"))
      (foreach n open_file_list
	(write-line n open_file)
      )
      (write-line new_grp_name open_file)
      (close open_file)
      ;cria o arquivo de subgrupos
      (setq open_file (open (strcat cnp_netroot "/quant/" cnqt_prefix cnqt_familia new_grp_code ".txt") "w" "utf8"))
      (write-line "Subgrupo 00" open_file)
      (close open_file)
      ;cria o arquivo-lista do primeiro subgrupo
      (setq open_file (open (strcat cnp_netroot "/quant/" cnqt_prefix cnqt_familia new_grp_code "00.txt") "w" "utf8"))
      (write-line "1;1.00;item 01" open_file)
      (close open_file)
      (q_update_data)
    );progn
  )
  (cnqt_start_readfile)
  (cnqt)
)
  
;ao selecionar um item da lista
(defun cnqt_selist ()
  (setq cnqt_selitem $value
	cnqt_code (strcat cnqt_prefix cnqt_familia cnqt_grp cnqt_sub cnqt_selitem))
  (cnqt_grayin)
  (cnqt_update_ppd)
)

;atualiza a lista, uma vez que o subgrupo é selecionado.
(defun cnqt_updlist ()
  (setq cnqt_sub $value)
  (if (= 1 (strlen cnqt_sub)) (setq cnqt_sub (strcat "0" cnqt_sub)))
  (setq cnqt_selitem "0")
  (setq cnqt_code (strcat cnqt_prefix cnqt_familia cnqt_grp cnqt_sub cnqt_selitem))
  (cnqt_updlist2)  
)

;continuação da anterior
(defun cnqt_updlist2 ()
  (setq cnqt_sublist_descr nil)
  (setq cnqt_sublist_type nil)
  (setq cnqt_currfile (strcat cnp_netroot "/quant/" cnqt_prefix cnqt_familia cnqt_grp cnqt_sub ".txt"))
  (setq open_file (open cnqt_currfile "r" "utf8"))
  (while (/= nil (setq linha (read-line open_file)))
    (cnqt_separa_dados)
    (setq cnqt_sublist_descr (append cnqt_sublist_descr (list item_text)))
  )
  (close open_file)
  (start_list "cnqt_list")
  (mapcar 'add_list cnqt_sublist_descr)
  (end_list)
  (set_tile "cnqt_list" cnqt_selitem)
  (cnqt_update_ppd)
)

;atualiza os subgrupos, depois de selecionado o grupo
(defun cnqt_updsub ()
  (setq cnqt_grp $value)
  (if (= 1 (strlen cnqt_grp)) (setq cnqt_grp (strcat "0" cnqt_grp)))
  (setq cnqt_selitem "0"
	cnqt_sub "00")
  (setq cnqt_code (strcat cnqt_prefix cnqt_familia cnqt_grp cnqt_sub cnqt_selitem))
  (cnqt_updlist2)
  (cnqt_updsub2)
)

;continuação da anterior
(defun cnqt_updsub2 ()
  (setq cnqt_sublist nil)
  (setq open_file (open (strcat cnp_netroot "/quant/" cnqt_prefix cnqt_familia cnqt_grp ".txt") "r" "utf8"))
  (while (/= nil (setq linha (read-line open_file)))
    (setq cnqt_sublist (append cnqt_sublist (list linha)))
  )
  (close open_file)
  (start_list "cnqt_subgroup")
  (mapcar 'add_list cnqt_sublist)
  (end_list)
  (set_tile "cnqt_subgroup" "0")
)

;atualiza a lista de grupos ao abrir a DCL ou selecionar uma família
(defun cnqt_updall ()
  (setq cnqt_grplist nil)
  (setq open_file (open (strcat cnp_netroot "/quant/" cnqt_prefix cnqt_familia ".txt") "r" "utf8"))
  (while (/= nil (setq linha (read-line open_file)))
    (setq cnqt_grplist (append cnqt_grplist (list linha)))
  )
  (close open_file)
  (start_list "cnqt_group")
  (mapcar 'add_list cnqt_grplist)
  (end_list)
  (set_tile "cnqt_group" cnqt_grp)
  (cnqt_updsub2)
  (cnqt_updlist2)
  (set_tile "cnqt_subgroup" cnqt_sub)
  (set_tile "cnqt_list" cnqt_selitem)
)

;dado o código (cnqt_code), separa os dados discriminados
(defun cnqt_define_data ()
  (setq cnqt_code_grupo (substr cnqt_code 1 6)
	cnqt_code_subgrupo (substr cnqt_code 7 2)
	cnqt_code_itemlist (substr cnqt_code 9 2)
	cnqt_code_item (substr cnqt_code 11)
	cnqt_code_grupo_n (1+ (fix (distof cnqt_code_subgrupo)))
	cnqt_code_subgrupo_n (1+ (fix (distof cnqt_code_itemlist)))
	cnqt_code_item_n (1+ (fix (distof cnqt_code_item)))
  )
  ;extrai o grupo
  (setq open_file (open (strcat cnp_netroot "/quant/" cnqt_code_grupo ".txt") "r" "utf8"))
  (repeat cnqt_code_grupo_n
    (setq grupo (read-line open_file))
  )
  (close open_file)
  ;extrai o subgrupo
  (setq open_file (open (strcat cnp_netroot "/quant/" cnqt_code_grupo cnqt_code_subgrupo ".txt") "r" "utf8"))
  (repeat cnqt_code_subgrupo_n
    (setq subgrupo (read-line open_file))
  )
  (close open_file)
  ;extrai o item
  (setq open_file (open (strcat cnp_netroot "/quant/" cnqt_code_grupo cnqt_code_subgrupo cnqt_code_itemlist ".txt") "r" "utf8"))
  (repeat cnqt_code_item_n
    (setq linha (read-line open_file))
  )
  (close open_file)
  (cnqt_separa_dados)
)

;atualiza as propriedades do item selecionado
(defun cnqt_update_ppd ()
  (cnqt_define_data)
  (cond
    ((= item_type "1") (set_tile "cnqt_show_type" "Tipo: Unitário") (setq updppd_sufix " (R$/unid.)"))
    ((= item_type "2") (set_tile "cnqt_show_type" "Tipo: Linear") (setq updppd_sufix " (R$/m)"))
    ((= item_type "3") (set_tile "cnqt_show_type" "Tipo: Área") (setq updppd_sufix " (R$/m2)"))
    ((= item_type "4") (set_tile "cnqt_show_type" "Tipo: Volume") (setq updppd_sufix " (R$/m3)"))
  )
  (set_tile "cnqt_show_custo" (strcat "Custo Unitário: " item_custo updppd_sufix))
)


;separa os dados de uma linha lida
(defun cnqt_separa_dados ()
  (setq cont1 1 n_pto "" item_type "" item_custo "" item_text "")
  (cnqt_extrai_n)
  (setq item_type n_pto n_pto "")
  (setq cont1 (1+ cont1))
  (cnqt_extrai_n)
  (setq item_custo n_pto n_pto "")
  (setq cont1 (1+ cont1))
  (setq item_text (substr linha cont1))
;;;  (cnqt_extrai_n)
;;;  (setq item_text n_pto n_pto "")
  (setq linha nil)
)

(defun cnqt_extrai_n ()
	(setq letra_n (substr linha cont1 1))
	(if (and (/= letra_n ";") (/= letra_n ""))
		(progn
			(setq n_pto (strcat n_pto letra_n))
			(setq cont1 (1+ cont1))
			(cnqt_extrai_n)
		);progn
	);if
);defun


;lô o arquivo de configuração incial
(defun cnqt_start_readfile ()
  (if (not (findfile (strcat cnp_root "/quant/last_code.txt")))
    (progn
      (setq open_file (open (strcat cnp_root "/quant/last_code.txt") "w" "utf8"))
      (write-line (strcat cnqt_prefix "0000000") open_file)
      (close open_file)
    )
  )
  (setq open_file (open (strcat cnp_root "/quant/last_code.txt") "r" "utf8")
	last_code (read-line open_file)
	cnqt_familia (substr last_code 5 2)
	cnqt_grp (substr last_code 7 2)
	cnqt_sub (substr last_code 9 2)
	cnqt_selitem (substr last_code 11)
  )
  (setq cnqt_code (strcat cnqt_prefix cnqt_familia cnqt_grp cnqt_sub cnqt_selitem))
)


;desabilita inicialmente os botões
(defun cnqt_grayout ()
  (mode_tile "cnqt_button_edit" 1)
  (mode_tile "cnqt_button_del" 1)
)

;desabilita inicialmente os botões
(defun cnqt_grayin ()
  (mode_tile "cnqt_button_edit" 0)
  (mode_tile "cnqt_button_del" 0)
)


;***********************************************************
;Outros comandos
;***********************************************************

;troca o código
(defun cnqt_change ()
  (cond
    ((= item_type "1") (setq s1 (ssget '((0 . "INSERT") (2 . "cnqt_ponto")))))
    ((= item_type "2") (setq s1 (ssget '((0 . "INSERT") (2 . "cnqt_linha")))))
    ((= item_type "3") (setq s1 (ssget '((0 . "INSERT") (or (2 . "cnqt_area") (2 . "cnqt_area"))))))
    ((= item_type "4") (setq s1 (ssget '((0 . "INSERT") (2 . "cnqt_volume")))))
  )
  (sssetfirst gripset (ssget "_P"))
  (initget "Sim Não")
  (setq alert_resp (getkword "\nConcorda com a seleção? <S/N>: "))
  (if (or (= alert_resp "Sim") (= alert_resp nil))
    (progn
      (sssetfirst nil)
      (setq s1_len (sslength s1)
	    counter 0
	    cnqt_insert_list nil
	    cnqt_ssent (ssadd)
      )
      (while (< counter s1_len)
	(setq e1 (ssname s1 counter)
	      e1_list (entget e1)
	      e1_blkname (cdr (assoc 2 e1_list))
	)
	(while (/= "SEQEND" (cdr (assoc 0 (setq selent (entget (setq e1 (entnext e1)))))))
	  (if (= "ATTRIB" (cdr (assoc 0 selent)))
	    (cond
	      ((= "CNQT" (strcase (cdr (assoc 2 selent))))
	       (setq e2_list (entget e1))
	       (setq e2_list (entmod (subst (cons 1 cnqt_code) (assoc 1 e2_list) e2_list)))
	       )
	      )
	    )
	  );while
	(setq counter (1+ counter))
      );while
    )
  )
)

;identificar código
(defun c:qid ()
  (prompt "\nSelecione o identificador que deseja verificar...")
  (setq ent (car (entsel)))
  (setq ent_list (entget ent))
  (if (not (= "INSERT" (strcase (cdr (assoc 0 ent_list)))))
    (progn
      (alert "O item selecionado\nnão é um bloco válido!")
      (exit)
    )
    (progn
      (setq blk_name (cdr (assoc 2 ent_list)))
      (cond
	((= (strcase blk_name t) "cnqt_ponto") (setq cnqt_show_type 1) (cd_extract))
	((= (strcase blk_name t) "cnqt_linha") (setq cnqt_show_type 2) (cd_extract))
	((= (strcase blk_name t) "cnqt_vertical") (setq cnqt_show_type 2) (cd_extract))
	((= (strcase blk_name t) "cnqt_area") (setq cnqt_show_type 3) (cd_extract))
	((= (strcase blk_name t) "cnqt_areav") (setq cnqt_show_type 3) (cd_extract))
	((= (strcase blk_name t) "cnqt_volume") (setq cnqt_show_type 4) (cd_extract))
	(t (alert "Bloco Inválido!") (exit))
      )
    )
  )
  (cd_show)
)

;abre a DCL mostrando os dados do código selecionado
(defun cd_show ()
  (setq dcl_id (load_dialog (strcat cnp_root "/lisp/cadnorma.dcl")))
  (if (not (new_dialog "cnqt_show" dcl_id)) (exit))
  (cond
    ((= ent_family "00") (set_tile "cnqt_show_family" "Arquitetura"))
    ((= ent_family "01") (set_tile "cnqt_show_family" "Tubulações"))
    ((= ent_family "02") (set_tile "cnqt_show_family" "Instalações Elétricas"))
  )
  (set_tile "cnqt_show_code" ent_code)
  (set_tile "cnqt_show_grupo" grupo)
  (set_tile "cnqt_show_subgrupo" subgrupo)
  (set_tile "cnqt_show_item" item_text)
  (cond
    ((= item_type "1") (set_tile "cnqt_show_type" "Unitário"))
    ((= item_type "2") (set_tile "cnqt_show_type" "Linear"))
    ((= item_type "3") (set_tile "cnqt_show_type" "Área"))
    ((= item_type "4") (set_tile "cnqt_show_type" "Volume"))
  )
  (set_tile "cnqt_show_quant1" ent_quant)
  (set_tile "cnqt_show_quant2" item_custo)
  (cond
    ((= cnqt_show_type 1)
     (set_tile "cnqt_show_unit1" "Unid.")
     (set_tile "cnqt_show_unit2" "(R$ / unid.)")
    )
    ((= cnqt_show_type 2)
     (set_tile "cnqt_show_unit1" "m")
     (set_tile "cnqt_show_unit2" "(R$ / m)")
    )
    ((= cnqt_show_type 3)
     (set_tile "cnqt_show_unit1" "m2")
     (set_tile "cnqt_show_unit2" "(R$ / m2)")
    )
    ((= cnqt_show_type 4)
     (set_tile "cnqt_show_unit1" "m3")
     (set_tile "cnqt_show_unit2" "(R$ / m3)")
    )
  )
  (setq cnqt_show_dcl (start_dialog))
  (unload_dialog dcl_id)
)

;extrai os dados a partir de um código fornecido : ent / ent_list
(defun cd_extract ()
  (while (/= "SEQEND" (cdr (assoc 0 (setq selent (entget (setq ent (entnext ent)))))))
    (if (= "ATTRIB" (cdr (assoc 0 selent)))
      (cond
	((= "QUANT" (cdr (assoc 2 selent))) (setq ent_quant (cdr (assoc 1 selent))))
	((= "CNQT" (cdr (assoc 2 selent))) (setq ent_code (cdr (assoc 1 selent))))
      )
    )
  )
  (setq ent_family (substr ent_code 5 2)
	ent_code_grupo (substr ent_code 1 6)
	ent_code_subgrupo (substr ent_code 7 2)
	ent_code_itemlist (substr ent_code 9 2)
	ent_code_item (substr ent_code 11)
	ent_code_grupo_n (1+ (fix (distof ent_code_subgrupo)))
	ent_code_subgrupo_n (1+ (fix (distof ent_code_itemlist)))
	ent_code_item_n (1+ (fix (distof ent_code_item)))
  )
  ;extrai o grupo
  (setq open_file (open (strcat cnp_netroot "/quant/" ent_code_grupo ".txt") "r" "utf8"))
  (repeat ent_code_grupo_n
    (setq grupo (read-line open_file))
  )
  (close open_file)
  ;extrai o subgrupo
  (setq open_file (open (strcat cnp_netroot "/quant/" ent_code_grupo ent_code_subgrupo ".txt") "r" "utf8"))
  (repeat ent_code_subgrupo_n
    (setq subgrupo (read-line open_file))
  )
  (close open_file)
  ;extrai o item
  (setq open_file (open (strcat cnp_netroot "/quant/" ent_code_grupo ent_code_subgrupo ent_code_itemlist ".txt") "r" "utf8"))
  (repeat ent_code_item_n
    (setq item (read-line open_file))
  )
  (close open_file)
  (setq linha item)
  (cnqt_separa_dados)
)

;verifica o código atual e a descrição correspondente
(defun cnqt_vc ()
  (if cnqt_code
    (progn
      (setq file (strcat cnp_netroot "/quant/" (substr cnqt_code 1 10) ".txt")
	    item (fix (distof (substr cnqt_code 11)))
	    open_file (open file "r" "utf8"))
      (repeat (1+ item)
	(setq linha (read-line open_file))
      )
      (close open_file)
    )
  )
)  


;****************************************************
;Seleções Unitárias
;****************************************************


;codificação de itens unitários
(defun cnqt_codify_unit ()
  (setq cnqt_selmode "0")
  (setq dcl_id (load_dialog (strcat cnp_root "/lisp/cadnorma.dcl")))
  (if (not (new_dialog "cnqt_codify_select" dcl_id)) (exit))
  (setq cnqt_sellist
	 (list
	   "Previous (Seleção Anterior)"
	   "Inserção Unitária"
	   "Selecionar bloco de exemplo"
	 )
  )
  (start_list "cnqt_codify_selist")
  (mapcar 'add_list cnqt_sellist)
  (end_list)
  (action_tile "cnqt_codify_selist" "(setq cnqt_selmode $value)")
  (set_tile "cnqt_codify_selist" cnqt_selmode)
  (setq cnqt_select_dcl (start_dialog))
  (unload_dialog dcl_id)
  (if (= 1 cnqt_select_dcl)
    (cond
      ((= cnqt_selmode "0") (cnqt_selmode_p1))
      ((= cnqt_selmode "1") (cnqt_selmode_p2))
      ((= cnqt_selmode "2") (cnqt_selmode_p3))
    )
  )
)

;Unitária em previous
(defun cnqt_selmode_p1 ()
  (if (= nil cnqt_repet)
    (progn
      (setq cnqt_repet 1)
      (setq cnqt_repet_str "1")
    )
  )
  (setq s1 (ssget "_P"))
  (sssetfirst gripset s1)
  (initget "Sim Não")
  (setq alert_resp (getkword "\nConcorda com a seleção? <S>/N: "))
  (if (= nil alert_resp) (setq alert_resp "Sim"))
  (if (= alert_resp "Sim")
    (progn
      (command "._undo" "_m")
      (setq dcl_id (load_dialog (strcat cnp_root "/lisp/cadnorma.dcl")))
      (if (not (new_dialog "cnqt_get_repet" dcl_id)) (exit))
      (set_tile "cnqt_getrep_repet" (rtos cnqt_repet 2 0))
      (mode_tile "cnqt_getrep_repet" 2)
      (action_tile "cnqt_getrep_repet" "(cnqt_getrep_very)")
      (action_tile "accept" "(done_dialog 1)")
      (action_tile "cancel" "(done_dialog 0)")
      (setq cnqt_h_dcl (start_dialog))
      (unload_dialog dcl_id)
      (cn7_find_blkscl)
      (cn7_verylayer "cnqt" 7)
      (setq s1_n (sslength s1) counter 0)
      (repeat s1_n
	(setq ent (ssname s1 counter)
	      ent_list (entget ent)
	      ent_type (cdr (assoc 0 ent_list)))
	(cond
	  ((= (strcase ent_type) "LINE")
	   (setq pt0 (cdr (assoc 10 ent_list))
		 pt2 (cdr (assoc 11 ent_list))
		 pt1 (polar pt0 (angle pt0 pt2) (/ (distance pt0 pt2) 2)))
	   (command "._insert" (strcat cnp_netroot "/quant/cnqt_ponto") "_s" cn7_blkscl "_non" pt1 0 cnqt_code cnqt_repet_str)
	  )
	  ((= (strcase ent_type) "ARC")
	   (setq pt1 (polar (cdr (assoc 10 ent_list)) (cdr (assoc 50 ent_list)) (cdr (assoc 40 ent_list))))
	   (command "._insert" (strcat cnp_netroot "/quant/cnqt_ponto") "_s" cn7_blkscl "_non" pt1 0 cnqt_code cnqt_repet_str)
	  )
	  ((= (strcase ent_type) "LWPOLYLINE")
	   (cnqt_lwpline)
	   (setq counter2 0)
	   (repeat (1- (length lwpline_list))
	     (setq pt0 (nth counter2 lwpline_list)
		   pt2 (nth (1+ counter2) lwpline_list)
		   pt1 (polar pt0 (angle pt0 pt2) (/ (distance pt0 pt2) 2))
		   counter2 (1+ counter2)
             )
	     (command "._insert" (strcat cnp_netroot "/quant/cnqt_ponto") "_s" cn7_blkscl "_non" pt1 0 cnqt_code cnqt_repet_str)
	   )
	   (if (= 1 (cdr (assoc 70 ent_list)))
	     (progn
	       (setq pt0 (nth counter2 lwpline_list)
		     pt2 (nth 0 lwpline_list)
		     pt1 (polar pt0 (angle pt0 pt2) (/ (distance pt0 pt2) 2))
		     counter2 (1+ counter2)
	       )
	       (command "._insert" (strcat cnp_netroot "/quant/cnqt_ponto") "_s" cn7_blkscl "_non" pt1 0 cnqt_code cnqt_repet_str)
	      )
	  )
	  )
	  (t (setq pt1 (cdr (assoc 10 ent_list)))
	   (command "._insert" (strcat cnp_netroot "/quant/cnqt_ponto") "_s" cn7_blkscl "_non" pt1 0 cnqt_code cnqt_repet_str)
	  )
	);cond
	(setq counter (1+ counter))
	(setq pt1 nil)
      )
    )
    (exit)
  )
  (princ)
)

;inserção Unitária
(defun cnqt_selmode_p2 ()
  (if (= nil cnqt_repet)
    (progn
      (setq cnqt_repet 1)
      (setq cnqt_repet_str "1")
    )
  )
  (setq pt1 (getpoint "\nPonto de inserção..."))
  (setq dcl_id (load_dialog (strcat cnp_root "/lisp/cadnorma.dcl")))
  (if (not (new_dialog "cnqt_get_repet" dcl_id)) (exit))
  (set_tile "cnqt_getrep_repet" (rtos cnqt_repet 2 0))
  (mode_tile "cnqt_getrep_repet" 2)
  (action_tile "cnqt_getrep_repet" "(cnqt_getrep_very)")
  (action_tile "accept" "(done_dialog 1)")
  (action_tile "cancel" "(done_dialog 0)")
  (setq cnqt_h_dcl (start_dialog))
  (unload_dialog dcl_id)
  (cn7_find_blkscl)
  (cn7_verylayer "cnqt" 7)
  (command "._insert" (strcat cnp_netroot "/quant/cnqt_ponto") "_s" cn7_blkscl "_non" pt1 "0" cnqt_code cnqt_repet_str)
  (exit)
  (princ)
)

;seleciona por bloco
(defun cnqt_selmode_p3 ()
  (prompt "\nSelecione um bloco de exemplo... ")
  (setq ent (entsel)
	ent_list (entget (car ent))
  )
  (setq ent_type (cdr (assoc 0 ent_list)))
  (if (= "INSERT" (strcase ent_type)) (setq blk_name (cdr (assoc 2 ent_list))))
  (prompt "\nSelecione a área a identificar os blocos... ")
  (setq s1 (ssget '((0 . "INSERT")))
	s1_len (sslength s1)
	counter 0
	cnqt_insert_list nil
	cnqt_ssent (ssadd))
  (while (< counter s1_len)
    (setq e1_list (entget (ssname s1 counter))
	  e1_blkname (cdr (assoc 2 e1_list)))
    (if (= blk_name e1_blkname)
      (setq cnqt_insert_list (append (list (cdr (assoc 10 e1_list))) cnqt_insert_list)
	    cnqt_ssent (ssadd (cdr (assoc -1 e1_list)) cnqt_ssent)
      )
    )
    (setq counter(1+ counter))
  )
  (sssetfirst gripset cnqt_ssent)
  (initget "Sim Não")
  (setq alert_resp (getkword "\nConcorda com a seleção? <S>/N: "))
  (if (= nil alert_resp) (setq alert_resp "Sim"))
  (if (= alert_resp "Sim")
    (progn
      (cn7_find_blkscl)
      (cn7_verylayer "cnqt" 7)
      (foreach n cnqt_insert_list
	(command "._insert" (strcat cnp_netroot "/quant/cnqt_ponto") "_s" cn7_blkscl "_non" n 0 cnqt_code "1")
      )
    )
  )
  (exit)
  (princ)
)

;funções auxiliares

;dada uma lwpolyline, constrói uma lista com os vértices
(defun cnqt_lwpline ()
  (setq ent_list_n (length ent_list)
	lwpline_list nil)
  (foreach n ent_list
    (if (= 10 (nth 0 n)) (setq lwpline_list (append (list (cdr n)) lwpline_list)))
  )
)


;****************************************************
;seleção linear
;****************************************************

;coleta o número de repetições em elementos lineares
(defun get_linrepet ()
  (if (= nil cnqt_repet)
    (progn
      (setq cnqt_repet 1)
      (setq cnqt_repet_str "1")
    )
  )
  (setq dcl_id (load_dialog (strcat cnp_root "/lisp/cadnorma.dcl")))
  (if (not (new_dialog "cnqt_get_repet" dcl_id)) (exit))
  (set_tile "cnqt_getrep_repet" (rtos cnqt_repet 2 0))
  (mode_tile "cnqt_getrep_repet" 2)
  (action_tile "cnqt_getrep_repet" "(cnqt_getrep_very)")
  (action_tile "accept" "(done_dialog 1)")
  (action_tile "cancel" "(done_dialog 0)")
  (setq cnqt_h_dcl (start_dialog))
  (unload_dialog dcl_id)
)


;codificação de itens lineares
(defun cnqt_codify_linear ()
  (setq cnqt_selmode "0")
  (setq dcl_id (load_dialog (strcat cnp_root "/lisp/cadnorma.dcl")))
  (if (not (new_dialog "cnqt_codify_select" dcl_id)) (exit))
  (setq cnqt_sellist
	 (list
	   "Previous (Seleção Anterior)"
	   "Selecionar 2 pontos"
	   "Selecionar uma linha"
	   "Selecionar conjunto de linhas"
	   "Cojunto de linhas, por layer"
	   "Selecionar Polyline"
	   "Linha Vertical"
	 )
  )
  (start_list "cnqt_codify_selist")
  (mapcar 'add_list cnqt_sellist)
  (end_list)
  (action_tile "cnqt_codify_selist" "(setq cnqt_selmode $value)")
  (set_tile "cnqt_codify_selist" cnqt_selmode)
  (setq cnqt_select_dcl (start_dialog))
  (unload_dialog dcl_id)
  (if (= 1 cnqt_select_dcl)
    (cond
      ((= cnqt_selmode "0") (cnqt_selmode_l1))
      ((= cnqt_selmode "1") (cnqt_selmode_l2))
      ((= cnqt_selmode "2") (cnqt_selmode_l3))
      ((= cnqt_selmode "3") (cnqt_selmode_l4))
      ((= cnqt_selmode "4") (cnqt_selmode_l5))
      ((= cnqt_selmode "5") (cnqt_selmode_l6))
      ((= cnqt_selmode "6") (cnqt_selmode_l7))
    )
  )
) 

;seleção anterior
(defun cnqt_selmode_l1 ()
  (setq s1 (ssget "_P"))
  (sssetfirst gripset s1)
  (initget "Sim Não")
  (setq alert_resp (getkword "\nConcorda com a seleção? <S>/N: "))
  (if (= nil alert_resp) (setq alert_resp "Sim"))
  (if (= alert_resp "Sim")
    (progn
      (command "._undo" "_m")
      (get_linrepet)
      (cn7_find_blkscl)
      (cn7_verylayer "cnqt" 7)
      (setq s1_n (sslength s1) counter 0)
      (repeat s1_n
	(setq ent (ssname s1 counter)
	      ent_list (entget ent)
	      ent_type (cdr (assoc 0 ent_list)))
	(cond
	  ((= (strcase ent_type) "LINE")
	   (setq pt0 (cdr (assoc 10 ent_list))
		 pt2 (cdr (assoc 11 ent_list))
		 dist (distance pt0 pt2)
		 pt1 (polar pt0 (angle pt0 pt2) (/ dist 2)))
	   (setq dist (* cnqt_repet dist))
	  (command "._insert" (strcat cnp_netroot "/quant/cnqt_linha") "_s" cn7_blkscl "_non" pt1 pt2 cnqt_code (rtos dist 2 2))
	  )
	  ((= (strcase ent_type) "ARC")
	   (setq arc_length (* (cdr (assoc 40 ent_list)) (- (cdr (assoc 51 ent_list)) (cdr (assoc 50 ent_list)))))
	   (setq pt1 (polar
		       (cdr (assoc 10 ent_list))
		       (+ (cdr (assoc 50 ent_list)) (/ (- (cdr (assoc 51 ent_list)) (cdr (assoc 50 ent_list))) 2))
		       (cdr (assoc 40 ent_list)))
           )
	   (setq arc_length (* cnqt_repet arc_length))
	   (command "._insert" (strcat cnp_netroot "/quant/cnqt_linha") "_s" cn7_blkscl "_non" pt1 0 cnqt_code (rtos arc_length 2 2))
	  )
	  ((= (strcase ent_type) "CIRCLE")
	   (command "._area" "_e" ent)
	   (setq pt1 (cdr (assoc 10 ent_list)))
	   (setq perim (* cnqt_repet (getvar "perimeter")))
	   (command "._insert" (strcat cnp_netroot "/quant/cnqt_linha") "_s" cn7_blkscl "_non" pt1 0 cnqt_code (rtos perim 2 2))
	  )
	  ((= (strcase ent_type) "LWPOLYLINE")
	   (cnqt_lwpline)
	   (setq counter2 0)
	   (repeat (1- (length lwpline_list))
	     (setq pt0 (nth counter2 lwpline_list)
		   pt2 (nth (1+ counter2) lwpline_list)
		   dist (distance pt0 pt2)
		   pt1 (polar pt0 (angle pt0 pt2) (/ (distance pt0 pt2) 2))
		   counter2 (1+ counter2)
             )
	     (setq dist (* cnqt_repet dist))
	     (command "._insert" (strcat cnp_netroot "/quant/cnqt_linha") "_s" cn7_blkscl "_non" pt1 "_non" pt2 cnqt_code (rtos dist 2 2))
	   )
	   (if (= 1 (cdr (assoc 70 ent_list)))
	     (progn
	       (setq pt0 (nth counter2 lwpline_list)
		     pt2 (nth 0 lwpline_list)
		     dist (distance pt0 pt2)
		     pt1 (polar pt0 (angle pt0 pt2) (/ (distance pt0 pt2) 2))
		     counter2 (1+ counter2)
	       )
	       (setq dist (* cnqt_repet dist))
	       (command "._insert" (strcat cnp_netroot "/quant/cnqt_linha") "_s" cn7_blkscl "_non" pt1 "_non" pt2 cnqt_code (rtos dist 2 2))
	      )
	   );if
	  );cond pline
	);cond
	(setq counter (1+ counter))
	(setq pt1 nil)
      )
    )
  )
  (exit)
  (princ)
)


;seleção de 2 pontos
(defun cnqt_selmode_l2 ()
  (setq pt1 (getpoint "\nPrimeiro ponto...")
	pt2 (getpoint pt1 "\nSegundo ponto... ")
	dist (distance pt1 pt2)
	pt3 (polar pt1 (angle pt1 pt2) (/ dist 2))
  )
  (get_linrepet)
  (setq dist (* cnqt_repet dist))
  (setq pt4 (getpoint "\nPonto de inserção do código...(ENTER = midpoint)... "))
  (if (/= nil pt4) (setq pt3 pt4))
  (cn7_find_blkscl)
  (cn7_verylayer "cnqt" 7)
  (command "._insert" (strcat cnp_netroot "/quant/cnqt_linha") "_s" cn7_blkscl "_non" pt3 pt2 cnqt_code (rtos dist 2 2))
  (exit)
  (princ)
)

;seleção de uma linha
(defun cnqt_selmode_l3 ()
  (prompt "\nSelecione uma linha... ")
  (setq ent (entsel)
	ent_list (entget (car ent))
	ent_type (cdr (assoc 0 ent_list)))
  (if (/= ent_type "LINE")
    (progn
      (alert "Entidade selecionada \nnão é uma linha!\nTente novamente...")
      (cnqt_selmode_l3)
    )
    (progn
      (setq pt1 (cdr (assoc 10 ent_list))
	    pt2 (cdr (assoc 11 ent_list))
	    dist (distance pt1 pt2)
	    pt3 (polar pt1 (angle pt1 pt2) (/ dist 2))
      )
      (get_linrepet)
      (setq dist (* cnqt_repet dist))
      (setq pt4 (getpoint "\nPonto de inserção do código...(ENTER = midpoint)... "))
      (if (/= nil pt4) (setq pt3 pt4))
      (cn7_find_blkscl)
      (cn7_verylayer "cnqt" 7)
      (command "._insert" (strcat cnp_netroot "/quant/cnqt_linha") "_s" cn7_blkscl "_non" pt3 pt2 cnqt_code (rtos dist 2 2))
    )
  )
  (exit)
  (princ)
)

;seleção de conjunto de linhas,
;independente de suas características
(defun cnqt_selmode_l4 ()
  (prompt "\nSelecione as linhas a codificar... ")
  (setq s1 (ssget '((0 . "LINE")))
	s1_len (sslength s1)
	counter 0
	cnqt_insert_list1 nil
	cnqt_insert_list2 nil)
  (sssetfirst gripset (ssget "_P"))
  (initget "Sim Não")
  (setq alert_resp (getkword "\nConcorda com a seleção? <S/N>: "))
  (if (= nil alert_resp) (setq alert_resp "Sim"))
  (if (or (= alert_resp "Sim") (= alert_resp nil))
    (progn
      (get_linrepet)
      (while (< counter s1_len)
	(setq e1_list (entget (ssname s1 counter))
	      e1_blklayer (cdr (assoc 8 e1_list)))
	(setq cnqt_insert_list1 (append (list (cdr (assoc 10 e1_list))) cnqt_insert_list1))
	(setq cnqt_insert_list2 (append (list (cdr (assoc 11 e1_list))) cnqt_insert_list2))
	(setq counter(1+ counter))
	)
      (cn7_find_blkscl)
      (cn7_verylayer "cnqt" 7)
      (setq counter 0 list_len (length cnqt_insert_list1))
      (repeat list_len
	(setq pt1 (nth counter cnqt_insert_list1)
	      pt2 (nth counter cnqt_insert_list2)
	      dist (distance pt1 pt2)
	      pt3 (polar pt1 (angle pt1 pt2) (/ dist 2))
	)
	(setq dist (* cnqt_repet dist))
	(command "._insert" (strcat cnp_netroot "/quant/cnqt_linha") "_s" cn7_blkscl "_non" pt3 pt2 cnqt_code (rtos dist 2 2))
	(setq counter (1+ counter))
      )
    )
  )
  (exit)
  (princ)
)

;seleção de conjunto de linhas, por layer
(defun cnqt_selmode_l5 ()
  (prompt "\nSelecione uma linha-tipo...")
  (setq ent (entsel)
	ent_list (entget (car ent))
  )
  (setq ent_type (cdr (assoc 0 ent_list)))
  (if (= "LINE" (strcase ent_type)) (setq blk_layer (cdr (assoc 8 ent_list))))
  (prompt "\nSelecione a área a identificar os blocos... ")
  (setq s1 (ssget '((0 . "LINE")))
	s1_len (sslength s1)
	counter 0
	cnqt_insert_list1 nil
	cnqt_insert_list2 nil
	cnqt_ssent (ssadd))
  (while (< counter s1_len)
    (setq e1_list (entget (ssname s1 counter))
	  e1_blklayer (cdr (assoc 8 e1_list)))
    (if (= blk_layer e1_blklayer)
      (progn
	(setq cnqt_insert_list1 (append (list (cdr (assoc 10 e1_list))) cnqt_insert_list1)
	      cnqt_insert_list2 (append (list (cdr (assoc 11 e1_list))) cnqt_insert_list2)
	      cnqt_ssent (ssadd (cdr (assoc -1 e1_list)) cnqt_ssent)
	)
	(setq counter(1+ counter))
      )
      (setq counter(1+ counter))
    )
  )
  (sssetfirst gripset cnqt_ssent)
  (initget "Sim Não")
  (setq alert_resp (getkword "\nConcorda com a seleção? <S>/N: "))
  (if (= nil alert_resp) (setq alert_resp "Sim"))
  (if (= alert_resp "Sim")
    (progn
      (get_linrepet)
      (cn7_find_blkscl)
      (cn7_verylayer "cnqt" 7)
      (setq counter 0 list_len (length cnqt_insert_list1))
      (repeat list_len
	(setq pt1 (nth counter cnqt_insert_list1)
	      pt2 (nth counter cnqt_insert_list2)
	      dist (distance pt1 pt2)
	      pt3 (polar pt1 (angle pt1 pt2) (/ dist 2))
	)
	(setq dist (* cnqt_repet dist))
	(command "._insert" (strcat cnp_netroot "/quant/cnqt_linha") "_s" cn7_blkscl "_non" pt3 pt2 cnqt_code (rtos dist 2 2))
	(setq counter (1+ counter))
      )
    )
  )
  (exit)
  (princ)
)

;denioteste
;seleção de poliline
(defun cnqt_selmode_l6 ()
  (prompt "\nSelecione uma polyline... ")
  (setq ent (entsel)
	ent_list (entget (car ent))
	ent_type (cdr (assoc 0 ent_list)))
  (if (/= ent_type "LWPOLYLINE")
    (progn
      (alert "Entidade selecionada \nnão é uma POLYLINE!\nTente novamente...")
      (cnqt_selmode_l6)
    )
    (progn
      (command "._select" (car ent) "")
      (sssetfirst gripset (ssget "_P"))
      (initget "Sim Não")
      (setq alert_resp (getkword "\nConcorda com a seleção? S/N... <ENTER>=S...: "))
      (if (or (= alert_resp "Sim") (= nil alert_resp))
	(progn
	  (get_linrepet)
	  (cnqt_lwpline)
	  (setq counter2 0)
	  (repeat (1- (length lwpline_list))
	    (setq pt0 (nth counter2 lwpline_list)
		  pt2 (nth (1+ counter2) lwpline_list)
		  dist (distance pt0 pt2)
		  pt1 (polar pt0 (angle pt0 pt2) (/ (distance pt0 pt2) 2))
		  counter2 (1+ counter2)
	    )
	    (setq dist (* cnqt_repet dist))
	    (command "._insert" (strcat cnp_netroot "/quant/cnqt_linha") "_s" cn7_blkscl "_non" pt1 "_non" pt2 cnqt_code (rtos dist 2 2))
	  )
	  (if (= 1 (cdr (assoc 70 ent_list)))
	    (progn
	      (setq pt0 (nth counter2 lwpline_list)
		    pt2 (nth 0 lwpline_list)
		    dist (distance pt0 pt2)
		    pt1 (polar pt0 (angle pt0 pt2) (/ (distance pt0 pt2) 2))
		    counter2 (1+ counter2)
	      )
	      (setq dist (* cnqt_repet dist))
	      (command "._insert" (strcat cnp_netroot "/quant/cnqt_linha") "_s" cn7_blkscl "_non" pt1 "_non" pt2 cnqt_code (rtos dist 2 2))
	    )
	  );if
	);progn
     );if
   )
  )
  (exit)
  (princ)
)

;****************************************************
;linha vertical
;****************************************************
(defun cnqt_selmode_l7 ()
  (if (not cnqt_h)
    (progn
      (setq cnqt_h 1.0)
      (setq cnqt_h_str "1.00")
    )
  )
  (setq dcl_id (load_dialog (strcat cnp_root "/lisp/cadnorma.dcl")))
  (if (not (new_dialog "cnqt_geth" dcl_id)) (exit))
  (set_tile "cnqt_geth_h" (rtos cnqt_h 2 2))
  (mode_tile "cnqt_geth_h" 2)
  (action_tile "cnqt_geth_h" "(cnqt_geth_very)")
  (action_tile "accept" "(done_dialog 1)")
  (setq cnqt_h_dcl (start_dialog))
  (unload_dialog dcl_id)
  (if (= 1 cnqt_h_dcl)
    (progn
      (get_linrepet)
      (cn7_find_blkscl)
      (cn7_verylayer "cnqt" 7)
      (setq pt1 (getpoint "\nPonto de inserção... "))
      (setq cnqt_h (* cnqt_repet cnqt_h))
      (command "._insert" (strcat cnp_netroot "/quant/cnqt_vertical") "_s" cn7_blkscl "_non" pt1 0 cnqt_code (rtos cnqt_h 2 2))
    )
  )
  (exit)
  (princ)
)


;verifica se a entrada é um número real
(defun cnqt_geth_very ()
  (setq cnqt_h_str $value)
  (if (distof cnqt_h_str)
    (setq cnqt_h (distof cnqt_h_str))
    (progn
      (done_dialog 0)
      (alert "Valor Inválido!")
    )
  )
)

;****************************************************
;Áreas
;****************************************************

;codificação de itens de área

;****************************************************
;Áreas Horizontais
;****************************************************

(defun cnqt_codify_area ()
  (setq cnqt_selmode "0")
  (setq dcl_id (load_dialog (strcat cnp_root "/lisp/cadnorma.dcl")))
  (if (not (new_dialog "cnqt_codify_select" dcl_id)) (exit))
  (setq cnqt_sellist
	 (list
	   "Inserção Manual de Código (fornecer área)"
	   "Área Horizontal: Seleção de vértices"
	   "Área Horizontal: Seleção de polyline"
	   "Área Horizontal: Pick point"
	   "Área Vertical: Selecionar dois pontos"
	   "Área Vertical: Selecionar uma linha"
	   "Área Vertical: Selecionar várias linhas"
	   "Área Vertical: Selecionar uma polyline"
	 )
  )
  (start_list "cnqt_codify_selist")
  (mapcar 'add_list cnqt_sellist)
  (end_list)
  (action_tile "cnqt_codify_selist" "(setq cnqt_selmode $value)")
  (set_tile "cnqt_codify_selist" cnqt_selmode)
  (setq cnqt_select_dcl (start_dialog))
  (unload_dialog dcl_id)
  (if (= 1 cnqt_select_dcl)
    (cond
      ((= cnqt_selmode "0") (cnqt_selmode_a0))
      ((= cnqt_selmode "1") (cnqt_selmode_a1))
      ((= cnqt_selmode "2") (cnqt_selmode_a2))
      ((= cnqt_selmode "3") (cnqt_selmode_a3))
      ((= cnqt_selmode "4") (cnqt_selmode_av1))
      ((= cnqt_selmode "5") (cnqt_selmode_av2))
      ((= cnqt_selmode "6") (cnqt_selmode_av3))
      ((= cnqt_selmode "7") (cnqt_selmode_av4))
    )
  )
)

;Inserção Manual Horizontal
(defun cnqt_selmode_a0 ()
  (setq cnqt_area (getvar "area"))
  (setq pt1 (getpoint "\nClique no ponto para inserção do código..."))
  (setq dcl_id (load_dialog (strcat cnp_root "/lisp/cadnorma.dcl")))
  (if (not (new_dialog "cnqt_getarea" dcl_id)) (exit))
  (set_tile "cnqt_get_area" (rtos cnqt_area 2 2))
  (mode_tile "cnqt_get_area" 2)
  (action_tile "cnqt_get_area" "(cnqt_getarea_very)")
  (action_tile "accept" "(done_dialog 1)")
  (action_tile "cancel" "(done_dialog 0)")
  (setq cnqt_area_dcl (start_dialog))
  (unload_dialog dcl_id)
  (if (= 1 cnqt_area_dcl)
    (progn
      (cn7_find_blkscl)
      (cn7_verylayer "cnqt" 7)
      (command "._insert" (strcat cnp_netroot "/quant/cnqt_area") "_s" cn7_blkscl "_non" pt1 "_non" 0 cnqt_code (rtos cnqt_area 2 2))
    )
  )
  (exit)
  (princ)
)

;clicar os pontos
(defun cnqt_selmode_a1 ()
  (setq a1_list nil)
  (setq pt1 (getpoint "\nPonto inicial..."))
  (if (= pt1 nil) (exit))
  (setq pt2 (getpoint pt1 "\nSegundo ponto..."))
  (if (= pt2 nil) (exit))
  (setq pt3 (getpoint pt2 "\nTerceiro ponto..."))
  (if (= pt3 nil) (exit))
  (setq a1_list (append (list pt1) (list pt2) (list pt3) a1_list))
  (while (/= nil (setq pt4 (getpoint pt3 "\nPróximo ponto... ")))
    (setq a1_list (append a1_list (list pt4)))
    (setq pt3 pt4)
  )
  (command "._area")
  (foreach n a1_list
    (command n)
  )
  (command "")
  (cn7_find_blkscl)
  (cn7_verylayer "cnqt" 7)
  (setq pt1 (getpoint "\nPonto para inserir o identificador... "))
  (command "._insert" (strcat cnp_netroot "/quant/cnqt_area") "_s" cn7_blkscl "_non" pt1 0 cnqt_code (rtos (getvar "area") 2 2))
  (exit)
  (princ)
)

;seleção de polyline
(defun cnqt_selmode_a2 ()
  (prompt "\nSelecione uma polyline... ")
  (setq ent (entsel)
	ent_list (entget (car ent))
	ent_type (cdr (assoc 0 ent_list)))
  (if (/= ent_type "LWPOLYLINE")
    (progn
      (alert "Entidade selecionada \nnão é uma POLYLINE!\nTente novamente...")
      (cnqt_selmode_l3)
    )
    (progn
      (command "._select" (car ent) "")
      (sssetfirst gripset (ssget "_P"))
      (initget "Sim Não")
      (setq alert_resp (getkword "\nConcorda com a seleção? <S/N>: "))
      (if (or (= alert_resp "Sim") (= alert_resp nil))
	(progn
	  (sssetfirst nil)
	  (command "._area" "_o" (car ent))
	  (cn7_find_blkscl)
	  (cn7_verylayer "cnqt" 7)
	  (setq pt1 (getpoint "\nPonto para inserir o identificador... "))
	  (command "._insert" (strcat cnp_netroot "/quant/cnqt_area") "_s" cn7_blkscl "_non" pt1 0 cnqt_code (rtos (getvar "area") 2 2))
	)
      )
    )
  )
  (exit)
  (princ)
)

;seleção por pick-point
(defun cnqt_selmode_a3 ()
  (setq colmo (getvar "cecolor"))
  (setq pt1 (getpoint "\nClique no ponto central..."))
  (setvar "cecolor" "214")
  (command "._boundary" pt1 ""  "._area" "_e" (entlast))
  (setvar "cecolor" colmo)
  (initget "Sim Não")
  (setq resp (getkword (strcat "\nÁrea=<" (rtos (getvar "area") 2 2) ">...Confirma área selecionada? <S/N>...(ENTER=Sim)... ")))
  (if (or (= resp "Sim") (= resp nil))
       (progn
	 (cn7_find_blkscl)
	 (cn7_verylayer "cnqt" 7)
	 (command "._area" "_o" (entlast))
	 (command "._erase" (entlast) "")
	 (setq pt1 (getpoint "\nPonto para inserir o identificador... "))
	 (command "._insert" (strcat cnp_netroot "/quant/cnqt_area") "_s" cn7_blkscl "_non" pt1 0 cnqt_code (rtos (getvar "area") 2 2))
       )
  )
  (exit)
  (princ)
)

;****************************************************
;Áreas Verticais
;****************************************************

;por dois pontos
(defun cnqt_selmode_av1 ()
  (if (= nil cnqt_h) (setq cnqt_h 1.00))
  (setq pt1 (getpoint "\nPrimeiro ponto...")
	pt2 (getpoint pt1 "\nSegundo ponto... ")
	dist (distance pt1 pt2)
	pt3 (polar pt1 (angle pt1 pt2) (/ dist 2)))
  (setq pt4 (getpoint "\nPonto de inserção do código...(ENTER = midpoint)... "))
  (if (/= nil pt4) (setq pt3 pt4))
  (setq dcl_id (load_dialog (strcat cnp_root "/lisp/cadnorma.dcl")))
  (if (not (new_dialog "cnqt_geth" dcl_id)) (exit))
  (set_tile "cnqt_geth_h" (rtos cnqt_h 2 2))
  (mode_tile "cnqt_geth_h" 2)
  (action_tile "cnqt_geth_h" "(cnqt_geth_very)")
  (action_tile "accept" "(done_dialog 1)")
  (action_tile "cancel" "(done_dialog 0)")
  (setq cnqt_h_dcl (start_dialog))
  (unload_dialog dcl_id)
  (if (= 1 cnqt_h_dcl)
    (progn
      (setq cnqt_area (* cnqt_h dist))
      (cn7_find_blkscl)
      (cn7_verylayer "cnqt" 7)
      (command "._insert" (strcat cnp_netroot "/quant/cnqt_areav") "_s" cn7_blkscl "_non" pt3 pt2 cnqt_code (rtos cnqt_area 2 2))
    )
  )
  (exit)
  (princ)
)

;selecionar uma linha
(defun cnqt_selmode_av2 ()
  (if (= nil cnqt_h) (setq cnqt_h 1.00))
  (prompt "\nSelecione uma linha... ")
    (setq ent (entsel)
	ent_list (entget (car ent))
	ent_type (cdr (assoc 0 ent_list)))
  (if (/= ent_type "LINE")
    (progn
      (alert "Entidade selecionada \nnão é uma LINHA (LINE)!\nTente novamente...")
      (cnqt_selmode_av2)
    )
    (progn
      (setq pt1 (cdr (assoc 10 ent_list))
	    pt2 (cdr (assoc 11 ent_list))
	    dist (distance pt1 pt2)
	    pt3 (polar pt1 (angle pt1 pt2) (/ dist 2))
      )
      (setq pt4 (getpoint "\nPonto de inserção do código...(ENTER = midpoint)... "))
      (if (/= nil pt4) (setq pt3 pt4))
      (setq dcl_id (load_dialog (strcat cnp_root "/lisp/cadnorma.dcl")))
      (if (not (new_dialog "cnqt_geth" dcl_id)) (exit))
      (set_tile "cnqt_geth_h" (rtos cnqt_h 2 2))
      (mode_tile "cnqt_geth_h" 2)
      (action_tile "cnqt_geth_h" "(cnqt_geth_very)")
      (action_tile "accept" "(done_dialog 1)")
      (action_tile "cancel" "(done_dialog 0)")
      (setq cnqt_h_dcl (start_dialog))
      (unload_dialog dcl_id)
      (if (= 1 cnqt_h_dcl)
	(progn
	  (setq cnqt_area (* cnqt_h dist))
	  (cn7_find_blkscl)
	  (cn7_verylayer "cnqt" 7)
	  (command "._insert" (strcat cnp_netroot "/quant/cnqt_areav") "_s" cn7_blkscl "_non" pt3 "_non" pt2 cnqt_code (rtos cnqt_area 2 2))
	)
      )
    )
  )
  (exit)
  (princ)
)


;selecionar várias linhas
(defun cnqt_selmode_av3 ()
  (if (= nil cnqt_h) (setq cnqt_h 1.00))
  (prompt "\nSelecione as linhas a codificar... ")
  (setq s1 (ssget '((0 . "LINE")))
	s1_len (sslength s1)
	counter 0
	cnqt_insert_list1 nil
	cnqt_insert_list2 nil)
  (sssetfirst gripset (ssget "_P"))
  (initget "Sim Não")
  (setq alert_resp (getkword "\nConcorda com a seleção? <S/N>:...<ENTER = S>...: ")) 
  (if (or (= alert_resp "Sim") (= alert_resp nil))
    (progn 
      (setq dcl_id (load_dialog (strcat cnp_root "/lisp/cadnorma.dcl")))
      (if (not (new_dialog "cnqt_geth" dcl_id)) (exit))
      (set_tile "cnqt_geth_h" (rtos cnqt_h 2 2))
      (mode_tile "cnqt_geth_h" 2)
      (action_tile "cnqt_geth_h" "(cnqt_geth_very)")
      (action_tile "accept" "(done_dialog 1)")
      (action_tile "cancel" "(done_dialog 0)")
      (setq cnqt_h_dcl (start_dialog))
      (unload_dialog dcl_id)
      (if (= 0 cnqt_h_dcl) (exit))
      (if (= 1 cnqt_h_dcl)
	(progn
	  (command "._undo" "_m")
	  (while (< counter s1_len)
	    (setq e1_list (entget (ssname s1 counter))
		  e1_blklayer (cdr (assoc 8 e1_list)))
	    (setq cnqt_insert_list1 (append (list (cdr (assoc 10 e1_list))) cnqt_insert_list1))
	    (setq cnqt_insert_list2 (append (list (cdr (assoc 11 e1_list))) cnqt_insert_list2))
	    (setq counter(1+ counter))
	  )
	  (cn7_find_blkscl)
	  (cn7_verylayer "cnqt" 7)
	  (setq counter 0 list_len (length cnqt_insert_list1))
	  (repeat list_len
	    (setq pt1 (nth counter cnqt_insert_list1)
		  pt2 (nth counter cnqt_insert_list2)
		  dist (distance pt1 pt2)
		  pt3 (polar pt1 (angle pt1 pt2) (/ dist 2))
	    )
	    (setq cnqt_area (* cnqt_h dist))
	    (command "._insert" (strcat cnp_netroot "/quant/cnqt_areav") "_s" cn7_blkscl "_non" pt3 pt2 cnqt_code (rtos cnqt_area 2 2))
	    (setq counter (1+ counter))
	  );repeat
	)
      )
    )
  )
  (exit)
  (princ)
)

;seleção de polyline
(defun cnqt_selmode_av4 ()
  (if (= nil cnqt_h) (setq cnqt_h 1.00))
  (prompt "\nSelecione uma polyline... ")
  (setq ent (entsel)
	ent_list (entget (car ent))
	ent_type (cdr (assoc 0 ent_list)))
  (if (/= ent_type "LWPOLYLINE")
    (progn
      (alert "Entidade selecionada \nnão é uma POLYLINE!\nTente novamente...")
      (cnqt_selmode_l3)
    )
    (progn
      (command "._select" (car ent) "")
      (sssetfirst gripset (ssget "_P"))
      (initget "Sim Não")
      (setq alert_resp (getkword "\nConcorda com a seleção? <S/N>: "))
      (if (or (= alert_resp "Sim") (= alert_resp nil))
	(progn
	  (sssetfirst nil)
	  (setq dcl_id (load_dialog (strcat cnp_root "/lisp/cadnorma.dcl")))
	  (if (not (new_dialog "cnqt_geth" dcl_id)) (exit))
	  (set_tile "cnqt_geth_h" (rtos cnqt_h 2 2))
	  (mode_tile "cnqt_geth_h" 2)
	  (action_tile "cnqt_geth_h" "(cnqt_geth_very)")
	  (action_tile "accept" "(done_dialog 1)")
	  (action_tile "cancel" "(done_dialog 0)")
	  (setq cnqt_h_dcl (start_dialog))
	  (unload_dialog dcl_id)
	  (if (= 1 cnqt_h_dcl)
	    (progn
	      (cn7_find_blkscl)
	      (cn7_verylayer "cnqt" 7)
	      )
	    (exit)
	  )
	  (cnqt_lwpline)
	  (setq counter2 0)
	  (command "._undo" "_m")
	  (repeat (1- (length lwpline_list))
	    (setq pt0 (nth counter2 lwpline_list)
		  pt2 (nth (1+ counter2) lwpline_list)
		  dist (distance pt0 pt2)
		  pt1 (polar pt0 (angle pt0 pt2) (/ (distance pt0 pt2) 2))
		  counter2 (1+ counter2)
		  )
	    (setq cnqt_area (* cnqt_h dist))
	    (command "._insert" (strcat cnp_netroot "/quant/cnqt_areav") "_s" cn7_blkscl "_non" pt1 "_non" pt2 cnqt_code (rtos cnqt_area 2 2))
	    )
	  (if (= 1 (cdr (assoc 70 ent_list)))
	    (progn
	      (setq pt0 (nth counter2 lwpline_list)
		    pt2 (nth 0 lwpline_list)
		    dist (distance pt0 pt2)
		    pt1 (polar pt0 (angle pt0 pt2) (/ (distance pt0 pt2) 2))
		    counter2 (1+ counter2)
		    )
	      (setq cnqt_area (* cnqt_h dist))
	      (command "._insert" (strcat cnp_netroot "/quant/cnqt_areav") "_s" cn7_blkscl "_non" pt1 pt2 cnqt_code (rtos cnqt_area 2 2))	)
	    );if
	  );progn
	(exit)
      );if
    );progn
  );if
  (exit)
  (princ)
);defun


;****************************************************
;Volumes
;****************************************************

;codificação de itens de área
(defun cnqt_codify_volume ()
  (setq cnqt_selmode "0")
  (setq dcl_id (load_dialog (strcat cnp_root "/lisp/cadnorma.dcl")))
  (if (not (new_dialog "cnqt_codify_select" dcl_id)) (exit))
  (setq cnqt_sellist
	 (list
	   "Inserção Manual de Código (fornecer volume)"
	   "Volume por Área: Seleção de vértices"
	   "Volume por Área: Seleção de polyline"
	   "Volume por Área: Pick point"
	   "Volume por Linha: Selecionar dois pontos"
	   "Volume por Linha: Selecionar uma linha"
	   "Volume por Linha: Selecionar várias linhas"
	   "Volume por Linha: Selecionar uma polyline"
	 )
  )
  (start_list "cnqt_codify_selist")
  (mapcar 'add_list cnqt_sellist)
  (end_list)
  (action_tile "cnqt_codify_selist" "(setq cnqt_selmode $value)")
  (set_tile "cnqt_codify_selist" cnqt_selmode)
  (setq cnqt_select_dcl (start_dialog))
  (unload_dialog dcl_id)
  (if (= 1 cnqt_select_dcl)
    (cond
      ((= cnqt_selmode "0") (cnqt_selmode_v0))
      ((= cnqt_selmode "1") (cnqt_selmode_v1))
      ((= cnqt_selmode "2") (cnqt_selmode_v2))
      ((= cnqt_selmode "3") (cnqt_selmode_v3))
      ((= cnqt_selmode "4") (cnqt_selmode_v4))
      ((= cnqt_selmode "5") (cnqt_selmode_v5))
      ((= cnqt_selmode "6") (cnqt_selmode_v6))
      ((= cnqt_selmode "7") (cnqt_selmode_v7))
    )
  )
)


;Inserção Manual
(defun cnqt_selmode_v0 ()
  (if (= nil cnqt_volume) (setq cnqt_volume 1.00))
  (setq pt1 (getpoint "\nClique no ponto para inserção do código..."))
  (setq dcl_id (load_dialog (strcat cnp_root "/lisp/cadnorma.dcl")))
  (if (not (new_dialog "cnqt_getvolume" dcl_id)) (exit))
  (set_tile "cnqt_get_volume" (rtos cnqt_volume 2 2))
  (mode_tile "cnqt_get_volume" 2)
  (action_tile "cnqt_get_volme" "(cnqt_getvolume_very)")
  (action_tile "accept" "(done_dialog 1)")
  (action_tile "cancel" "(done_dialog 0)")
  (setq cnqt_volume_dcl (start_dialog))
  (unload_dialog dcl_id)
  (if (= 1 cnqt_volume_dcl)
    (progn
      (cn7_find_blkscl)
      (cn7_verylayer "cnqt" 7)
      (command "._insert" (strcat cnp_netroot "/quant/cnqt_volume") "_s" cn7_blkscl "_non" pt1 "_non" 0 cnqt_code (rtos cnqt_volume 2 2))
    )
  )
  (exit)
  (princ)
)


;****************************************************
;Volume por Áreas Horizontais
;****************************************************

;Seleção de vértices
(defun cnqt_selmode_v1 ()
  (if (= nil cnqt_h) (setq cnqt_h 1.00))
  (setq a1_list nil)
  (setq pt1 (getpoint "\nPonto inicial..."))
  (if (= pt1 nil) (exit))
  (setq pt2 (getpoint pt1 "\nSegundo ponto..."))
  (if (= pt2 nil) (exit))
  (setq pt3 (getpoint pt2 "\nTerceiro ponto..."))
  (if (= pt3 nil) (exit))
  (setq a1_list (append (list pt1) (list pt2) (list pt3) a1_list))
  (while (/= nil (setq pt4 (getpoint pt3 "\nPróximo ponto... ")))
    (setq a1_list (append a1_list (list pt4)))
    (setq pt3 pt4)
  )
  (command "._area")
  (foreach n a1_list
    (command n)
  )
  (command "")
  (cn7_find_blkscl)
  (cn7_verylayer "cnqt" 7)
  (setq pt1 (getpoint "\nPonto para inserir o identificador... "))
  (setq dcl_id (load_dialog (strcat cnp_root "/lisp/cadnorma.dcl")))
  (if (not (new_dialog "cnqt_geth" dcl_id)) (exit))
  (set_tile "cnqt_geth_h" (rtos cnqt_h 2 2))
  (mode_tile "cnqt_geth_h" 2)
  (action_tile "cnqt_geth_h" "(cnqt_geth_very)")
  (action_tile "accept" "(done_dialog 1)")
  (action_tile "cancel" "(done_dialog 0)")
  (setq cnqt_h_dcl (start_dialog))
  (unload_dialog dcl_id)
  (if (= 1 cnqt_h_dcl)
    (progn
      (setq cnqt_volume (* cnqt_h (getvar "area")))
      (cn7_find_blkscl)
      (cn7_verylayer "cnqt" 7)
      (command "._insert" (strcat cnp_netroot "/quant/cnqt_volume") "_s" cn7_blkscl "_non" pt1 0 cnqt_code (rtos cnqt_volume 2 2))
    )
  )
  (exit)
  (princ)
)

;Seleção de polyline
(defun cnqt_selmode_v2 ()
  (if (= nil cnqt_h) (setq cnqt_h 1.00))
  (prompt "\nSelecione a Polyline para cálculo de área... ")
  (setq ent (entsel))
  (command "._select" (car ent) "")
  (sssetfirst gripset (ssget "_P"))
  (initget "Sim Não")
  (setq alert_resp (getkword "\nConcorda com a seleção? <S/N>:...<ENTER = S>...: "))
  (if (or (= alert_resp "Sim") (= alert_resp nil))
    (progn
      (command "._area" "_o" (car ent))
      (cn7_find_blkscl)
      (cn7_verylayer "cnqt" 7)
      (setq dcl_id (load_dialog (strcat cnp_root "/lisp/cadnorma.dcl")))
      (if (not (new_dialog "cnqt_geth" dcl_id)) (exit))
      (set_tile "cnqt_geth_h" (rtos cnqt_h 2 2))
      (mode_tile "cnqt_geth_h" 2)
      (action_tile "cnqt_geth_h" "(cnqt_geth_very)")
      (action_tile "accept" "(done_dialog 1)")
      (action_tile "cancel" "(done_dialog 0)")
      (setq cnqt_h_dcl (start_dialog))
      (unload_dialog dcl_id)
      (if (= 1 cnqt_h_dcl)
	(progn
	  (setq cnqt_volume (* cnqt_h (getvar "area")))
	  (cn7_find_blkscl)
	  (cn7_verylayer "cnqt" 7)
	  (setq pt1 (getpoint "\nPonto para inserir o identificador... "))
	  (command "._insert" (strcat cnp_netroot "/quant/cnqt_volume") "_s" cn7_blkscl "_non" pt1 0 cnqt_code (rtos cnqt_volume 2 2))
	 )
      )
    )
  )
  (exit)
  (princ)
)

;Por pick-point
(defun cnqt_selmode_v3 ()
  (if (= nil cnqt_h) (setq cnqt_h 1.00))
  (setq colmo (getvar "cecolor"))
  (setq pt1 (getpoint "\nClique no ponto central..."))
  (setvar "cecolor" "214")
  (command "._boundary" pt1 ""  "._area" "_e" (entlast))
  (setvar "cecolor" colmo)
  (initget "Sim Não")
  (setq resp (getkword (strcat "\nÁrea=<" (rtos (getvar "area") 2 2) ">...Confirma área selecionada? <S/N>...(ENTER=Sim)... ")))
  (if (or (= resp "Sim") (= resp nil))
       (progn
	 (command "._area" "_o" (entlast))
	 (command "._erase" (entlast) "")
	 (setq pt1 (getpoint "\nPonto para inserir o identificador... "))
	 (setq dcl_id (load_dialog (strcat cnp_root "/lisp/cadnorma.dcl")))
	 (if (not (new_dialog "cnqt_geth" dcl_id)) (exit))
	 (set_tile "cnqt_geth_h" (rtos cnqt_h 2 2))
	 (mode_tile "cnqt_geth_h" 2)
	 (action_tile "cnqt_geth_h" "(cnqt_geth_very)")
	 (action_tile "accept" "(done_dialog 1)")
	 (action_tile "cancel" "(done_dialog 0)")
	 (setq cnqt_h_dcl (start_dialog))
	 (unload_dialog dcl_id)
	 (if (= 1 cnqt_h_dcl)
	   (progn
	     (setq cnqt_volume (* cnqt_h (getvar "area")))
	     (cn7_find_blkscl)
	     (cn7_verylayer "cnqt" 7)
	     (command "._insert" (strcat cnp_netroot "/quant/cnqt_volume") "_s" cn7_blkscl "_non" pt1 0 cnqt_code (rtos cnqt_volume 2 2))
	     )
	   )
	 )
  )
  (exit)
  (princ)
)

;****************************************************
;Volume por Linhas
;****************************************************

;por dois pontos
(defun cnqt_selmode_v4 ()
  (if (= nil cnqt_h) (setq cnqt_h 1.00))
  (if (= nil cnqt_esp) (setq cnqt_esp 1.00))
  (setq pt1 (getpoint "\nPrimeiro ponto...")
	pt2 (getpoint pt1 "\nSegundo ponto... ")
	dist (distance pt1 pt2)
	pt3 (polar pt1 (angle pt1 pt2) (/ dist 2)))
  (setq dcl_id (load_dialog (strcat cnp_root "/lisp/cadnorma.dcl")))
  (if (not (new_dialog "cnqt_get_harea" dcl_id)) (exit))
  (set_tile "cnqt_geth_h" (rtos cnqt_h 2 2))
  (mode_tile "cnqt_geth_h" 2)
  (action_tile "cnqt_geth_h" "(cnqt_geth_very)")
  (set_tile "cnqt_get_esp" (rtos cnqt_esp 2 2))
  (mode_tile "cnqt_get_esp" 2)
  (action_tile "cnqt_get_esp" "(cnqt_getesp_very)")
  (action_tile "accept" "(done_dialog 1)")
  (action_tile "cancel" "(done_dialog 0)")
  (setq cnqt_h_dcl (start_dialog))
  (unload_dialog dcl_id)
  (if (= 1 cnqt_h_dcl)
    (progn
      (setq cnqt_volume (* dist cnqt_h cnqt_esp))
      (cn7_find_blkscl)
      (cn7_verylayer "cnqt" 7)
      (command "._insert" (strcat cnp_netroot "/quant/cnqt_volume") "_s" cn7_blkscl "_non" pt3 pt2 cnqt_code (rtos cnqt_volume 2 2))
    )
  )
  (exit)
  (princ)
)

;selecionar uma linha
(defun cnqt_selmode_v5 ()
  (if (= nil cnqt_h) (setq cnqt_h 1.00))
  (if (= nil cnqt_esp) (setq cnqt_esp 1.00))
  (prompt "\nSelecione uma linha... ")
    (setq ent (entsel)
	ent_list (entget (car ent))
	ent_type (cdr (assoc 0 ent_list)))
  (if (/= ent_type "LINE")
    (progn
      (alert "Entidade selecionada \nnão é uma LINHA (LINE)!\nTente novamente...")
      (cnqt_selmode_v5)
    )
    (progn
      (setq pt1 (cdr (assoc 10 ent_list))
	    pt2 (cdr (assoc 11 ent_list))
	    dist (distance pt1 pt2)
	    pt3 (polar pt1 (angle pt1 pt2) (/ dist 2))
      )
      (setq dcl_id (load_dialog (strcat cnp_root "/lisp/cadnorma.dcl")))
      (if (not (new_dialog "cnqt_get_harea" dcl_id)) (exit))
      (set_tile "cnqt_geth_h" (rtos cnqt_h 2 2))
      (mode_tile "cnqt_geth_h" 2)
      (action_tile "cnqt_geth_h" "(cnqt_geth_very)")
      (set_tile "cnqt_get_esp" (rtos cnqt_esp 2 2))
      (mode_tile "cnqt_get_esp" 2)
      (action_tile "cnqt_get_esp" "(cnqt_getesp_very)")
      (action_tile "accept" "(done_dialog 1)")
      (action_tile "cancel" "(done_dialog 0)")
      (setq cnqt_h_dcl (start_dialog))
      (unload_dialog dcl_id)
      (if (= 1 cnqt_h_dcl)
	(progn
	  (setq cnqt_volume (* dist cnqt_h cnqt_esp))
	  (cn7_find_blkscl)
	  (cn7_verylayer "cnqt" 7)
	  (command "._insert" (strcat cnp_netroot "/quant/cnqt_volume") "_s" cn7_blkscl "_non" pt3 pt2 cnqt_code (rtos cnqt_volume 2 2))
	)
      )
    )
  )
  (exit)
  (princ)
)

;selecionar várias linhas
(defun cnqt_selmode_v6 ()
  (if (= nil cnqt_h) (setq cnqt_h 1.00))
  (if (= nil cnqt_esp) (setq cnqt_esp 1.00))
  (prompt "\nSelecione as linhas a codificar... ")
  (setq s1 (ssget '((0 . "LINE")))
	s1_len (sslength s1)
	counter 0
	cnqt_insert_list1 nil
	cnqt_insert_list2 nil)
  (sssetfirst gripset (ssget "_P"))
  (initget "Sim Não")
  (setq alert_resp (getkword "\nConcorda com a seleção? <S/N>:...<ENTER = S>...: ")) 
  (if (or (= alert_resp "Sim") (= alert_resp nil))
    (progn 
      (setq dcl_id (load_dialog (strcat cnp_root "/lisp/cadnorma.dcl")))
      (if (not (new_dialog "cnqt_get_harea" dcl_id)) (exit))
      (set_tile "cnqt_geth_h" (rtos cnqt_h 2 2))
      (mode_tile "cnqt_geth_h" 2)
      (action_tile "cnqt_geth_h" "(cnqt_geth_very)")
      (set_tile "cnqt_get_esp" (rtos cnqt_esp 2 2))
      (mode_tile "cnqt_get_esp" 2)
      (action_tile "cnqt_get_esp" "(cnqt_getesp_very)")
      (action_tile "accept" "(done_dialog 1)")
      (action_tile "cancel" "(done_dialog 0)")
      (setq cnqt_h_dcl (start_dialog))
      (unload_dialog dcl_id)
      (if (= 1 cnqt_h_dcl)
	(progn
	  (while (< counter s1_len)
	    (setq e1_list (entget (ssname s1 counter))
		  e1_blklayer (cdr (assoc 8 e1_list)))
	    (setq cnqt_insert_list1 (append (list (cdr (assoc 10 e1_list))) cnqt_insert_list1))
	    (setq cnqt_insert_list2 (append (list (cdr (assoc 11 e1_list))) cnqt_insert_list2))
	    (setq counter(1+ counter))
	  )
	  (cn7_find_blkscl)
	  (cn7_verylayer "cnqt" 7)
	  (setq counter 0 list_len (length cnqt_insert_list1))
	  (repeat list_len
	    (setq pt1 (nth counter cnqt_insert_list1)
		  pt2 (nth counter cnqt_insert_list2)
		  dist (distance pt1 pt2)
		  pt3 (polar pt1 (angle pt1 pt2) (/ dist 2))
	    )
	    (setq cnqt_volume (* cnqt_h cnqt_esp dist))
	    (command "._insert" (strcat cnp_netroot "/quant/cnqt_volume") "_s" cn7_blkscl "_non" pt3 pt2 cnqt_code (rtos cnqt_volume 2 2))
	    (setq counter (1+ counter))
	  );repeat
	)
      )
    )
  )
  (exit)
  (princ)
)


;seleção de polyline
(defun cnqt_selmode_v7 ()
  (if (= nil cnqt_h) (setq cnqt_h 1.00))
  (if (= nil cnqt_esp) (setq cnqt_esp 1.00))
  (prompt "\nSelecione uma polyline... ")
  (setq ent (entsel)
	ent_list (entget (car ent))
	ent_type (cdr (assoc 0 ent_list)))
  (if (/= ent_type "LWPOLYLINE")
    (progn
      (alert "Entidade selecionada \nnão é uma POLYLINE!\nTente novamente...")
      (cnqt_selmode_v7)
    )
    (progn
      (command "._select" (car ent) "")
      (sssetfirst gripset (ssget "_P"))
      (initget "Sim Não")
      (setq alert_resp (getkword "\nConcorda com a seleção? <S/N>:...<ENTER = S>...: "))
      (if (or (= alert_resp "Sim") (= alert_resp nil))
	(progn
	  (setq dcl_id (load_dialog (strcat cnp_root "/lisp/cadnorma.dcl")))
	  (if (not (new_dialog "cnqt_get_harea" dcl_id)) (exit))
	  (set_tile "cnqt_geth_h" (rtos cnqt_h 2 2))
	  (mode_tile "cnqt_geth_h" 2)
	  (action_tile "cnqt_geth_h" "(cnqt_geth_very)")
	  (set_tile "cnqt_get_esp" (rtos cnqt_esp 2 2))
	  (mode_tile "cnqt_get_esp" 2)
	  (action_tile "cnqt_get_esp" "(cnqt_getesp_very)")
	  (action_tile "accept" "(done_dialog 1)")
	  (action_tile "cancel" "(done_dialog 0)")
	  (setq cnqt_h_dcl (start_dialog))
	  (unload_dialog dcl_id)
	  (if (= 1 cnqt_h_dcl)
	    (progn
	      (cnqt_lwpline)
	      (setq counter2 0)
	      (command "._undo" "_m")
	      (repeat (1- (length lwpline_list))
		(setq pt0 (nth counter2 lwpline_list)
		      pt2 (nth (1+ counter2) lwpline_list)
		      dist (distance pt0 pt2)
		      pt1 (polar pt0 (angle pt0 pt2) (/ (distance pt0 pt2) 2))
		      counter2 (1+ counter2)
		      )
		(setq cnqt_volume (* cnqt_h cnqt_esp dist))
		(command "._insert" (strcat cnp_netroot "/quant/cnqt_volume") "_s" cn7_blkscl "_non" pt1 pt2 cnqt_code (rtos cnqt_volume 2 2))
	      )
	      (if (= 1 (cdr (assoc 70 ent_list)))
		(progn
		  (setq pt0 (nth counter2 lwpline_list)
			pt2 (nth 0 lwpline_list)
			dist (distance pt0 pt2)
			pt1 (polar pt0 (angle pt0 pt2) (/ (distance pt0 pt2) 2))
			counter2 (1+ counter2)
			)
		  (setq cnqt_volume (* cnqt_h cnqt_esp dist))
		  (command "._insert" (strcat cnp_netroot "/quant/cnqt_volume") "_s" cn7_blkscl "_non" pt1 pt2 cnqt_code (rtos cnqt_volume 2 2))
	      )
	    );if
	);progn
      );if
    )
	))
  );if
  (exit)
  (princ)
);defun


;verifica se a entrada é um número real
(defun cnqt_geth_very ()
  (setq cnqt_h_str $value)
  (if (distof cnqt_h_str)
    (setq cnqt_h (distof cnqt_h_str))
    (progn
      (done_dialog 0)
      (alert "Valor Inválido!")
    )
  )
)

;verifica se a entrada é um número real
(defun cnqt_getarea_very ()
  (setq cnqt_area_str $value)
  (if (distof cnqt_area_str)
    (setq cnqt_area (distof cnqt_area_str))
    (progn
      (done_dialog 0)
      (alert "Valor Inválido!")
    )
  )
)


;******************************************************
;QuantNorma - Relatório
;******************************************************

;Importação de dados para tabela
(defun c:qimp ()
  (setq qtable_list nil)
  (setq arq1 (getfiled "Selecione o Arquivo de Dados" (getvar "dwgprefix") "csv" 4))
  (setq open_file (open arq1 "r" "utf8"))
  (while (/= nil (setq linha (read-line open_file)))
    (cnqt_separa_dados2)
    (setq lista (list cnqt_code item_ordem item_text item_quant item_unit item_custo item_custotal))
    (setq qtable_list (append qtable_list (list lista)))
  )
  (close open_file)
  (if (= item_custotal "")
    (q_rel_drawtable)
    (q_rel_drawtable2)
  )

)

;separ os dados de uma linha (6 dados)
(defun cnqt_separa_dados2 ()
  (setq cont1 1 n_pto "" cnqt_code "" item_ordem "" item_text ""
	item_quant "" item_unit "" item_custo "" item_custotal "")
  (cnqt_extrai_n)
  (setq cnqt_code n_pto n_pto "")
  (setq cont1 (1+ cont1))
  (cnqt_extrai_n)
  (setq item_ordem n_pto n_pto "")
  (setq cont1 (1+ cont1))
  (cnqt_extrai_n)
  (setq item_text n_pto n_pto "")
  (setq cont1 (1+ cont1))
  (cnqt_extrai_n)
  (setq item_quant n_pto n_pto "")
  (setq cont1 (1+ cont1))
  (cnqt_extrai_n)
  (setq item_unit n_pto n_pto "")
  (setq cont1 (1+ cont1))
  (cnqt_extrai_n)
  (setq item_custo n_pto n_pto "")
  (setq cont1 (1+ cont1))
  (cnqt_extrai_n)
  (setq item_custotal n_pto n_pto "")
)

;exportação de dados para outro desenho
(defun c:qexp ()
  (q_rel_select);gera new_list
  (q_rel_formtable)
  (q_rel_final_table)
  (setq arq1 (getfiled "Selecione o Arquivo de Dados" (getvar "dwgprefix") "csv" 1))
  (setq open_file (open arq1 "w" "utf8"))
  (foreach n qtable_list
    (if (= q_rel_tabletype "q_rel_table1")
      (write-line (strcat (nth 0 n) ";" (nth 1 n) ";" (nth 2 n) ";" (nth 3 n) ";" (nth 4 n)) open_file)
      (write-line (strcat (nth 0 n) ";" (nth 1 n) ";" (nth 2 n) ";" (nth 3 n) ";" (nth 4 n) ";" (nth 5 n) ";" (nth 6 n)) open_file)
    )
  )
  (close open_file)
  (prompt (strcat "Dados Exportados com sucesso para " arq1))
  (princ)
)

;criar tabela neste desenho
(defun c:qtab ()
  (q_rel_select)
  (q_rel_formtable)
  (q_rel_final_table)
  (if (= q_rel_tabletype "q_rel_table1")
    (q_rel_drawtable)
    (q_rel_drawtable2)
  )
)

;Analisa a lista, item por item, extrai os dados e forma a lista de itens: qtable_list
(defun q_rel_final_table ()
  (setq counter 1
	qtable_list nil
  )
  (foreach n new_list
    (setq cnqt_code (nth 0 n)
	  cnqt_quant (nth 1 n)
    )
    (cnqt_define_data)
    (cond
      ((= item_type "1") (setq cnqt_unit "unid."))
      ((= item_type "2") (setq cnqt_unit "m"))
      ((= item_type "3") (setq cnqt_unit "m2"))
      ((= item_type "4") (setq cnqt_unit "m3"))
    )
    (setq cnqt_custotal (rtos (* (distof cnqt_quant) (distof item_custo)) 2 2))
    (if (= q_rel_tabletype "q_rel_table1")
      (setq item_list (list cnqt_code (rtos counter 2 0) item_text cnqt_quant cnqt_unit))
      (setq item_list (list cnqt_code (rtos counter 2 0) item_text cnqt_quant cnqt_unit item_custo cnqt_custotal))
    )
    (setq qtable_list (append qtable_list (list item_list)))
    (setq counter (1+ counter))
  )
)


;formatação de tabela
(defun q_rel_formtable ()
  (if (not q_rel_tabletype) (setq q_rel_tabletype "q_rel_table1"))
  (setq dcl_id (load_dialog (strcat cnp_root "/lisp/cadnorma.dcl")))
  (if (not (new_dialog "cnqt_rel_formtable" dcl_id)) (exit))
  (set_tile "q_rel_tabletype" q_rel_tabletype)
  (action_tile "q_rel_tabletype" "(setq q_rel_tabletype $value)")
  (action_tile "cancel" "(done_dialog 0)")
  (action_tile "accept" "(done_dialog 1)")
  (setq cnqt_rel_formtable_dcl (start_dialog))
  (unload_dialog dcl_id)
)   


;Seleção e separação de objetos: new_list
(defun q_rel_select ()
  (prompt "\nSelecione o trecho que deseja quantificar... ")
  (setq s1 (ssget '((0 . "INSERT")))
	s1_len (sslength s1)
	counter 0
	rel_selist (ssadd)
	full_list nil
	ent_quant nil
  )
  ;analisa cada elemento selecionado e constroi a lista geral
  (while (< counter s1_len)
    (setq e1 (ssname s1 counter)
	  e1_list (entget e1)
	  e1_blkname (cdr (assoc 2 e1_list)))
    (if (or (= (strcase e1_blkname t) "cnqt_ponto")
	    (= (strcase e1_blkname t) "cnqt_area")
	    (= (strcase e1_blkname t) "cnqt_vertical")
	    (= (strcase e1_blkname t) "cnqt_linha")
	    (= (strcase e1_blkname t) "cnqt_areav")
	    (= (strcase e1_blkname t) "cnqt_volume")
	 )
      (progn
	(setq rel_selist (ssadd e1 rel_selist))
	(while (/= "SEQEND" (cdr (assoc 0 (setq selent (entget (setq e1 (entnext e1)))))))
	  (if (= "ATTRIB" (cdr (assoc 0 selent)))
	    (cond
	      ((= "QUANT" (cdr (assoc 2 selent))) (setq ent_quant (cdr (assoc 1 selent))))
	      ((= "CNQT" (cdr (assoc 2 selent))) (setq ent_code (cdr (assoc 1 selent))))
	    )
	  )
	)
	(setq temp_list (list ent_code ent_quant)
	      full_list (append (list temp_list) full_list)
	)
      )
    )
    (setq counter (1+ counter))
  );while
  (setq full_list2 full_list)  
  (setq full_list (vl-sort full_list
	   (function (lambda (e1 e2) (< (nth 0 e1) (nth 0 e2))))))
  (sssetfirst gripset rel_selist)
  (rel_orglist)
  (sssetfirst nil)
)

;Desenha tabela só de quantitativos;;;;;   denio
(defun q_rel_drawtable ()
  (setq grupo nil subgrupo nil grupo_last nil subgrupo_last nil)
  (if (not (tblsearch "style" "quantnorma_text"))
    (command  "._style" "quantnorma_text"  "romans" "0" "" "" "" "" "")
    (setvar "textstyle" "quantnorma_text")
  )
  (setq item_counter 1)
  (initget 128)
  (setq p0 (getpoint "\nPonto superior esquerdo da tabela... <L> para migrar para o Layout..."))
  (cond      
    ((= 'STR  (type p0))
      (cond
         ((= "L" (strcase p0))
	   (if (= 0 (getvar "tilemode"))
	    (command "._pspace")
	    (progn
	      (command "._tilemode" "0")
	      (command "._pspace")
	    )
	   )
	   (initget 1)
	   (setq p0 (getpoint "\nClique no ponto superior esquerdo da tabela..."))
	 )
	 (t
	  (prompt "\nOpção inválida! Digite 'L' ou marque o primeiro ponto...")
	  (q_rel_drawtable)
	 )
       )
     )
  )
  (cn7_find_blkscl)
  (cn7_verylayer "cnqt" 7)
  (rel_draw_cabeçalho)
  (setq rel_grupo nil
	rel_subgrupo nil
  )	
  (foreach n qtable_list
    (if grupo (setq grupo_last grupo))
    (if subgrupo (setq subgrupo_last subgrupo))
    (rel_extract)
    (if (/= grupo_last grupo)
      (progn
	(rel_draw_grupo)
	(rel_draw_subgrupo)
	(rel_draw_cabitem)
      )
      (if (/= subgrupo_last subgrupo)
	(progn
	  (rel_draw_subgrupo)
	)
      )
    )
    (rel_draw_item)
    (rel_close_sub)
    (rel_close_table)
    (setq item_counter (1+ item_counter))
  )
)

;desenha tabela completa
(defun q_rel_drawtable2 ()
  (setq grupo nil subgrupo nil grupo_last nil subgrupo_last nil)
  (if (not (tblsearch "style" "quantorma_text"))
    (command  "._style" "quantorma_text"  "romans" "0" "" "" "" "" "")
    (setvar "textstyle" "quantorma_text")
  )
  (setq item_counter 1)
  (initget 128)
  (setq p0 (getpoint "\nPonto superior esquerdo da tabela... <L> para migrar para o Layout..."))
  (cond      
    ((= 'STR  (type p0))
      (cond
         ((= "L" (strcase p0))
	   (if (= 0 (getvar "tilemode"))
	    (command "._pspace")
	    (progn
	      (command "._tilemode" "0")
	      (command "._pspace")
	    )
	   )
	   (initget 1)
	   (setq p0 (getpoint "\nClique no ponto superior esquerdo da tabela..."))
	 )
	 (t
	  (prompt "\nOpção inválida! Digite 'L' ou marque o primeiro ponto...")
	  (q_rel_drawtable2)
	 )
       )
     )
  )
  (cn7_find_blkscl)
  (cn7_verylayer "cnqt" 7)
  (rel_draw_cabeçalho)
  (setq rel_grupo nil
	rel_subgrupo nil
  )	
  (foreach n qtable_list
    (if grupo (setq grupo_last grupo))
    (if subgrupo (setq subgrupo_last subgrupo))
    (rel_extract)
    (if (/= grupo_last grupo)
      (progn
	(rel_draw_grupo)
	(rel_draw_subgrupo)
	(rel_draw_cabitem2)
      )
      (if (/= subgrupo_last subgrupo)
	(progn
	  (rel_draw_subgrupo)
	)
      )
    )
    (rel_draw_item)
    (rel_close_sub)
    (rel_close_table)
    (setq item_counter (1+ item_counter))
  )
)
  

;extrai de n (elemto da new_list) família, grupo e subgrupo
(defun rel_extract ()
  (setq rel_code (nth 0 n)
	cnqt_code rel_code
	rel_item (nth 1 n)
	rel_item (nth 2 n)
	rel_quant (nth 3 n)
	rel_unit (nth 4 n)
	rel_custo (nth 5 n)
	rel_total (nth 6 n)
	rel_familia (substr rel_code 1 6)
	rel_grupo (substr rel_code 7 2)
	rel_subgrupo (substr rel_code 9 2)
	rel_item (substr rel_code 11)
  )
  (setq open_file (open (strcat cnp_netroot "/quant/" rel_familia ".txt") "r" "utf8"))
  (repeat (1+ (fix (distof rel_grupo)))
    (setq grupo (read-line open_file))
  )
  (close open_file)
  (setq open_file (open (strcat cnp_netroot "/quant/" rel_familia rel_grupo ".txt") "r" "utf8"))
  (repeat (1+ (fix (distof rel_subgrupo)))
    (setq subgrupo (read-line open_file))
  )
  (close open_file)
  (setq open_file (open (strcat cnp_netroot "/quant/" rel_familia rel_grupo rel_subgrupo ".txt") "r" "utf8"))
  (repeat (1+ (fix (distof rel_item)))
    (setq item (read-line open_file))
  )
  (close open_file)
  (setq linha item)
  (cnqt_separa_dados)
)

;desenha o cabeçalho da tabela
(defun rel_draw_cabeçalho ()
  (setq p0_1 (polar p0 0 (* cn7_blkscl 17.5))
	p0_1a (polar p0 0 (* cn7_blkscl 8.75))
	p0_1b (polar p0_1a (/ (* 3 pi) 2) (* cn7_blkscl 0.4))
	p0_2 (polar p0 (/ (* 3 pi) 2) (* cn7_blkscl 0.8))
	p0_3 (polar p0_2 0 (* cn7_blkscl 17.5))
  )
  (setvar "cecolor" "6")
  (command "._line" "_non" p0 "_non" p0_1 "" "._line" "_non" p0_2 "_non" p0_3 "")
  (setvar "cecolor" "5")
  (command "._text" "_m" "_non" p0_1b (* cn7_blkscl 0.35) "0" "LISTA DE MATERIAIS")
)

;desenha 0 cabeçalho de grupo
(defun rel_draw_grupo ()
  (setq	p0_2 (polar p0_2 (/ (* 3 pi) 2) (* cn7_blkscl 0.5))
	p0_3 (polar p0_2 0 (* cn7_blkscl 17.5))
	p0_2a (polar p0_2 0 (* cn7_blkscl 8.75))
	p0_2b (polar p0_2a (/ pi 2) (* cn7_blkscl 0.25))
  )
  (setvar "cecolor" "5")
  (command "._line" "_non" p0_2 "_non" p0_3 "")
  (setvar "cecolor" "4")
  (command "._text" "_m" "_non" p0_2b (* cn7_blkscl 0.30) "0" grupo)
)

;desenha o cabeçalho de subgrupo
(defun rel_draw_subgrupo ()
  (setq	p0_2 (polar p0_2 (/ (* 3 pi) 2) (* cn7_blkscl 0.5))
	p0_3 (polar p0_2 0 (* cn7_blkscl 17.5))
	p0_2a (polar p0_2 0 (* cn7_blkscl 0.12))
	p0_2b (polar p0_2a (/ pi 2) (* cn7_blkscl 0.25))
  )
  (setvar "cecolor" "5")
  (command "._line" "_non" p0_2 "_non" p0_3 "")
  (setvar "cecolor" "3")
  (command "._text" "_ml" "_non" p0_2b (* cn7_blkscl 0.25) "0" subgrupo)
  (setq p0_2_xa (polar p0_2 0 (* cn7_blkscl 1.0))
	p0_2_xb (polar p0_2 0 (* cn7_blkscl 2.5))
	p0_2_xc (polar p0_2 0 (* cn7_blkscl 4.0))
	p0_2_xd (polar p0_2 0 (* cn7_blkscl 13.5))
	p0_2_xe (polar p0_2 0 (* cn7_blkscl 15.5))
  )
)

;desenha o cabeçalho de item
(defun rel_draw_cabitem ()
  (setq	p0_2 (polar p0_2 (/ (* 3 pi) 2) (* cn7_blkscl 0.5))
	p0_3 (polar p0_2 0 (* cn7_blkscl 17.5))
	p0_2a (polar p0_2 0 (* cn7_blkscl 0.5))
	p0_2b (polar p0_2a (/ pi 2) (* cn7_blkscl 0.25))
	p0_2c (polar p0_2b 0 (* cn7_blkscl 1.25))
	p0_2d (polar p0_2c 0 (* cn7_blkscl 1.5))
	p0_2e (polar p0_2d 0 (* cn7_blkscl 6.25))
  )
  (setvar "cecolor" "5")
  (command "._line" "_non" p0_2 "_non" p0_3 "")
  (setvar "cecolor" "3")
  (command "._text" "_mc" "_non" p0_2b (* cn7_blkscl 0.25) "0" "ITEM")
  (command "._text" "_mc" "_non" p0_2c (* cn7_blkscl 0.25) "0" "QUANT")
  (command "._text" "_mc" "_non" p0_2d (* cn7_blkscl 0.25) "0" "UND")
  (command "._text" "_mc" "_non" p0_2e (* cn7_blkscl 0.25) "0" "DESCRIÇÃO")
)

;desenha o cabeçalho de item para tabela completa
(defun rel_draw_cabitem2 ()
  (setq	p0_2 (polar p0_2 (/ (* 3 pi) 2) (* cn7_blkscl 0.5))
	p0_3 (polar p0_2 0 (* cn7_blkscl 17.5))
	p0_2a (polar p0_2 0 (* cn7_blkscl 0.5))
	p0_2b (polar p0_2a (/ pi 2) (* cn7_blkscl 0.25))
	p0_2c (polar p0_2b 0 (* cn7_blkscl 1.25))
	p0_2d (polar p0_2c 0 (* cn7_blkscl 1.5))
	p0_2e (polar p0_2d 0 (* cn7_blkscl 4.75))
	p0_2f (polar p0_2d 0 (* cn7_blkscl 11.25))
	p0_2g (polar p0_2d 0 (* cn7_blkscl 13.25))
  )
  (setvar "cecolor" "5")
  (command "._line" "_non" p0_2 "_non" p0_3 "")
  (setvar "cecolor" "3")
  (command "._text" "_mc" "_non" p0_2b (* cn7_blkscl 0.25) "0" "ITEM")
  (command "._text" "_mc" "_non" p0_2c (* cn7_blkscl 0.25) "0" "QUANT")
  (command "._text" "_mc" "_non" p0_2d (* cn7_blkscl 0.25) "0" "UND")
  (command "._text" "_mc" "_non" p0_2e (* cn7_blkscl 0.25) "0" "DESCRIÇÃO")
  (command "._text" "_mc" "_non" p0_2f (* cn7_blkscl 0.25) "0" "R$/Un")
  (command "._text" "_mc" "_non" p0_2g (* cn7_blkscl 0.25) "0" "R$")
)

  

;desenha o item
(defun rel_draw_item ()
  (setq	p0_2 (polar p0_2 (/ (* 3 pi) 2) (* cn7_blkscl 0.4))
	p0_3 (polar p0_2 0 (* cn7_blkscl 17.5))
	p0_2a (polar p0_2 0 (* cn7_blkscl 0.5))
	p0_2b (polar p0_2a (/ pi 2) (* cn7_blkscl 0.2))
	p0_2c (polar p0_2b 0 (* cn7_blkscl 1.25))
	p0_2d (polar p0_2c 0 (* cn7_blkscl 1.5))
	p0_2e (polar p0_2d 0 (* cn7_blkscl 1.0))
	p0_2f (polar p0_2e 0 (* cn7_blkscl 11.0))
	p0_2g (polar p0_2f 0 (* cn7_blkscl 2.0))
  )
  (setvar "cecolor" "5")
  (command "._line" "_non" p0_2 "_non" p0_3 "")
  (setvar "cecolor" "2")
  (command "._text" "_mc" "_non" p0_2b (* cn7_blkscl 0.2) "0" (rtos item_counter 2 0))
  (command "._text" "_mc" "_non" p0_2c (* cn7_blkscl 0.2) "0" rel_quant)
  (command "._text" "_mc" "_non" p0_2d (* cn7_blkscl 0.2) "0" rel_unit)
  (command "._text" "_ml" "_non" p0_2e (* cn7_blkscl 0.2) "0" item_text)
  (if (= q_rel_tabletype "q_rel_table2")
    (progn
      (command "._text" "_mr" "_non" p0_2f (* cn7_blkscl 0.2) "0" rel_custo)
      (command "._text" "_mr" "_non" p0_2g (* cn7_blkscl 0.2) "0" rel_total)
    )
  )
  (setq p0_2_ya (polar p0_2 0 (* cn7_blkscl 1.0))
	p0_2_yb (polar p0_2 0 (* cn7_blkscl 2.5))
	p0_2_yc (polar p0_2 0 (* cn7_blkscl 4.0))
	p0_2_yd (polar p0_2 0 (* cn7_blkscl 13.5))
	p0_2_ye (polar p0_2 0 (* cn7_blkscl 15.5))
  )
)

;desenha as linhas verticais da tabela entre os subgrupos
(defun rel_close_sub ()
  (setvar "cecolor" "3")
  (command "._line" "_non" p0_2_xa "_non" p0_2_ya "")
  (command "._line" "_non" p0_2_xb "_non" p0_2_yb "")
  (command "._line" "_non" p0_2_xc "_non" p0_2_yc "")
  (if (= q_rel_tabletype "q_rel_table2")
    (progn
      (command "._line" "_non" p0_2_xd "_non" p0_2_yd "")
      (command "._line" "_non" p0_2_xe "_non" p0_2_ye "")
    )
  )
)

;desenha o contorno da tabela
(defun rel_close_table ()
  (setvar "cecolor" "6")
  (command "._line" "_non" p0 "_non" p0_2 "_non" p0_3 "_non" p0_1 "")
)  


;organiza a lista, eliminando repetições e somando quantidades
(defun rel_orglist ()
  (setq counter 0 new_list nil)
  (while (< counter (length full_list))
    (setq e1 (nth counter full_list))
    (if (nth (1+ counter) full_list)
      (progn
	(setq e2 (nth (1+ counter) full_list))
	(rel_testa)
      )
      (progn
	(setq new_list (append new_list (list e1)))
	(setq counter (1+ counter))
      )
    )
  )
  (while (not (equal full_list new_list))
  (setq full_list new_list counter 0 new_list nil)
  (while (< counter (length full_list))
    (setq e1 (nth counter full_list))
    (if (nth (1+ counter) full_list)
      (progn
	(setq e2 (nth (1+ counter) full_list))
	(rel_testa)
      )
      (progn
	(setq new_list (append new_list (list e1)))
	(setq counter (1+ counter))
      )
    )
  )
  )
)

;verifica se acabou a lista
(defun rel_testa ()
  (if (/= (nth 0 e1) (nth 0 e2))
    (progn
      (setq new_list (append new_list (list e1)))
      (setq counter (1+ counter))
    )
    (progn
      (setq new_quant (rtos (+ (distof (nth 1 e1)) (distof (nth 1 e2))) 2 2)
	    new_element (list (nth 0 e1) new_quant)
	    new_list (append new_list (list new_element))
      )
      (setq counter (+ 2 counter))
    )
  )
)

;verifica se a entrada é um número real
(defun cnqt_geth_very ()
  (setq cnqt_h_str $value)
  (if (distof cnqt_h_str)
    (setq cnqt_h (distof cnqt_h_str))
    (progn
      (done_dialog 0)
      (alert "Valor Inválido!")
    )
  )
)

;verifica se a entrada é um número real
(defun cnqt_getarea_very ()
  (setq cnqt_area_str $value)
  (if (distof cnqt_area_str)
    (setq cnqt_area (distof cnqt_area_str))
    (progn
      (done_dialog 0)
      (alert "Valor Inválido!")
    )
  )
)

;verifica se a entrada é um número real
(defun cnqt_getesp_very ()
  (setq cnqt_esp_str $value)
  (if (distof cnqt_esp_str)
    (setq cnqt_esp (distof cnqt_esp_str))
    (progn
      (done_dialog 0)
      (alert "Valor Inválido!")
    )
  )
)

;verifica se a entrada é um número real
(defun cnqt_getrep_very ()
  (setq cnqt_repet_str $value)
  (if (distof cnqt_repet_str)
    (setq cnqt_repet (distof cnqt_repet_str))
    (progn
      (done_dialog 0)
      (alert "Valor Inválido!")
    )
  )
)

;função que atualiza a data da última modificação na base de dados
(defun q_update_data ()
  (setq curr_date (rtos (getvar "cdate") 2 4))
  (setq qbak_date_file1 (open (strcat cnp_netroot "/quant/qdate.txt") "w" "utf8"))
  (write-line curr_date qbak_date_file1)
  (close qbak_date_file1)
)

;função que faz o backup
(defun c:qbak ()
  (q_update_data)
  (cnp:copy-dir (strcat cnp_netroot "/quant") (strcat cnp_netroot "/quant_backup"))
)

;função que restaura o backup
(defun c:qrst ()
  (setq file1 (open (strcat cnp_netroot "/quant/qdate.txt") "r" "utf8")
	data1 (read-line file1)
	file2 (open (strcat cnp_netroot "/quant_backup/qdate.txt") "r" "utf8")
	data2 (read-line file2)
	data1_text (strcat (substr data1 7 2) "/" (substr data1 5 2) "/" (substr data1 1 4) " - "
			   (substr data1 10 2) ":" (substr data1 12 2) " h")
	data2_text (strcat (substr data2 7 2) "/" (substr data2 5 2) "/" (substr data2 1 4) " - "
			   (substr data2 10 2) ":" (substr data2 12 2) " h")
  )
  (close file1)
  (close file2)
  (setq alert_resp nil)
  (cn7_alert_yes_no
    (strcat "Última Modificação = " data1_text)
    (strcat "Último Backup Feito = " data2_text)
    "Deseja realmente restaurar o backup?"
  )
  (if (= alert_resp "yes")
    (cnp:copy-dir (strcat cnp_netroot "/quant_backup") (strcat cnp_netroot "/quant"))
  )
)

;cnp_33 - Gráficos




;******************************************************************************
;******************************************************************************
;gráficos
;******************************************************************************
;******************************************************************************


;******************************************************************************
;Formatar os Gráficos *********************************************************
;******************************************************************************

(defun c:grf ()
  (if (/= cn7_dwgunit 1.0)
    (progn
      (cn7_alert_ok
	  "Por enquanto, os gráficos aplicam-se"
	  "apenas para desenhos em metros!"
	  "Aguardem novas atualizações..."
      )
      (exit)
     )
  )
  (cn7_altext_readfile)
  (cn7_init)
  (defgraf_file)
  (defgraf_dcl)
  (princ)
)
  
;lê os dados iniciais da DCL no arquivo de dados
(defun defgraf_file ()
  (if (findfile (strcat cnp_root "/config/graformat.txt"))
    (defgraf_readfile)
    (progn
      (setq file (open (strcat cnp_root "/config/graformat.txt") "w" "utf8"))
      (write-line "4" file)
      (write-line "3" file)
      (write-line "9" file)
      (write-line "0" file)
      (write-line "5" file)
      (write-line "3" file)
      (close file)
      (defgraf_readfile)
    )
  )
)

;função que lê o arquivo de dados
(defun defgraf_readfile ()
  (setq	file (open (strcat cnp_root"/config/graformat.txt") "r" "utf8"))
  (setq	graf_eix (read-line file))
  (setq	graf_tik (read-line file))
  (setq	graf_grd (read-line file))
  (setq	graf_glt (read-line file))
  (setq	graf_txc (read-line file))
  (setq	graf_txs (read-line file))
  (close file)
)

(defun defgraf_dcl ()
  (setq dcl_id (load_dialog (strcat cnp_root "/lisp/cadnorma.dcl")))
  (if (not (new_dialog "def_graf" dcl_id)) (exit))
  ;eixos
  (start_image "grf_eix_color")
  (fill_image  0  0
    (dimx_tile "grf_eix_color")
    (dimy_tile "grf_eix_color")
    (fix (distof graf_eix))
  )
  (end_image)
  (action_tile "grf_eix_color" "(grf_eixcolor)")
  ;tick
  (start_image "grf_tik_color")
  (fill_image  0  0
    (dimx_tile "grf_tik_color")
    (dimy_tile "grf_tik_color")
    (fix (distof graf_tik))
  )
  (end_image)
  (action_tile "grf_tik_color" "(grf_tikcolor)")
  ;grid
  (start_image "grf_grd_color")
  (fill_image  0  0
    (dimx_tile "grf_grd_color")
    (dimy_tile "grf_grd_color")
    (fix (distof graf_grd))
  )
  (end_image)
  (action_tile "grf_grd_color" "(grf_grdcolor)")
  ;linetype da grade
  (setq grf_grdlty (list "Continuous" "hidden" "hidden2"))
  (start_list "grf_grd_ltype")
  (mapcar 'add_list grf_grdlty)
  (end_list)
  (set_tile "grf_grd_ltype" graf_glt)
  (action_tile "grf_grd_ltype" "(setq graf_glt $value)")
  ;cor do texto
  (start_image "grf_txt_color")
  (fill_image  0  0
    (dimx_tile "grf_txt_color")
    (dimy_tile "grf_txt_color")
    (fix (distof graf_txc))
  )
  (end_image)
  (action_tile "grf_txt_color" "(grf_txccolor)")
  ;estilo do texto
  (setq grf_txlist (list "r50" "r60" "r70" "r80" "r90" "r100" "r120" "r140" "r175" "r200"
			    "t1" "t2" "t3" "t4" "t5" "t6" "t7"))
  (start_list "grf_txt_style")
  (mapcar 'add_list grf_txlist)
  (end_list)
  (set_tile "grf_txt_style" graf_txs)
  (action_tile "grf_txt_style" "(setq graf_txs $value)")

  (action_tile "accept" "(done_dialog 1)")
  (action_tile "cancel" "(done_dialog 0)")
  (setq defgraf_dialog (start_dialog))
  (unload_dialog dcl_id)
  (if (= 1 defgraf_dialog) (defgraf_ok))
)

;botão ok
(defun defgraf_ok ()
  (setq file2 (open (strcat cnp_root "/config/graformat.txt") "w" "utf8"))
  (write-line graf_eix file2)
  (write-line graf_tik file2)
  (write-line graf_grd file2)
  (write-line graf_glt file2)
  (write-line graf_txc file2)
  (write-line graf_txs file2)
  (close file2)
)

(defun defgraf_readfile ()
  (setq	file (open (strcat cnp_root "/config/graformat.txt") "r" "utf8"))
  (setq	graf_eix (read-line file))
  (setq	graf_tik (read-line file))
  (setq	graf_grd (read-line file))
  (setq	graf_glt (read-line file))
  (setq	graf_txc (read-line file))
  (setq	graf_txs (read-line file))
  (close file)
)

;escolher cor dos textos
(defun grf_txccolor ()
  (setq grf_txc_newcol (acad_colordlg (fix (distof graf_txc))))
  (if (/= nil grf_txc_newcol) (setq graf_txc (rtos grf_txc_newcol 2 0)))
  (start_image "grf_txt_color")
  (fill_image  0  0
    (dimx_tile "grf_txt_color")
    (dimy_tile "grf_txt_color")
    (fix (distof graf_txc))
  )
  (end_image)
)


;escolher cor das grades
(defun grf_grdcolor ()
  (setq grf_grd_newcol (acad_colordlg (fix (distof graf_grd))))
  (if (/= nil grf_grd_newcol) (setq graf_grd (rtos grf_grd_newcol 2 0)))
  (start_image "grf_grd_color")
  (fill_image  0  0
    (dimx_tile "grf_grd_color")
    (dimy_tile "grf_grd_color")
    (fix (distof graf_grd))
  )
  (end_image)
)

;escolher cor dos ticks
(defun grf_tikcolor ()
  (setq grf_tik_newcol (acad_colordlg (fix (distof graf_tik))))
  (if (/= nil grf_tik_newcol) (setq graf_tik (rtos grf_tik_newcol 2 0)))
  (start_image "grf_tik_color")
  (fill_image  0  0
    (dimx_tile "grf_tik_color")
    (dimy_tile "grf_tik_color")
    (fix (distof graf_tik))
  )
  (end_image)
)

;escolher cor dos eixos
(defun grf_eixcolor ()
  (setq grf_eix_newcol (acad_colordlg (fix (distof graf_eix))))
  (if (/= nil grf_eix_newcol) (setq graf_eix (rtos grf_eix_newcol 2 0)))
  (start_image "grf_eix_color")
  (fill_image  0  0
    (dimx_tile "grf_eix_color")
    (dimy_tile "grf_eix_color")
    (fix (distof graf_eix))
  )
  (end_image)
)


;******************************************************************************
; DESENHA OS EIXOS NAS ESCALAS DETERMINADAS -> DCL
;******************************************************************************
(defun c:gre ()
  (cn7_init)
  (if (/= cn7_dwgunit 1.0)
    (progn
      (cn7_alert_ok
	  "Por enquanto, os gráficos aplicam-se"
	  "apenas para desenhos em metros!"
	  "Aguardem novas atualizações..."
      )
      (exit)
     )
  )
  ;verifica se está no Paper Space
  (if (and (= (getvar "tilemode") 0) (= 1 (getvar "cvport")))
    (progn
      (cn7_alert_ok
	"Os gráficos só podem ser"
	"contruídos no Model Space"
	"ou em uma Viewport Ativa.")
      (exit)
    )
  )
  ;define a escala horizontal
  (setq grp_type "2")
  (cn7_find_blkscl)
  (defgraf_readfile)
  (drweixo_file)
  (setq drweixo_hz_scal (rtos (getvar "userr3") 2 2))
  (setq graf_stylist (list "r50" "r60" "r70" "r80" "r90" "r100" "r120" "r140" "r175" "r200"
			   "t1" "t2" "t3" "t4" "t5" "t6" "t7"))
  (setq cn7_txtsty (nth (fix (distof graf_txs)) graf_stylist))
  (cn7_text_hfinal)
  (cn7_text_height)
  ;abre a DCL
  (setq dcl_id (load_dialog (strcat cnp_root "/lisp/cadnorma.dcl")))
  (if (not (new_dialog "graf_eixos" dcl_id)) (exit))
  ;escala horizontal
  (set_tile "hz_scale" drweixo_hz_scal)
  (mode_tile "hz_scale" 1)
  ;x mínimo
  (set_tile "hz_xmin" drweixo_hz_xmin)
  (action_tile "hz_xmin" "(setq drweixo_hz_xmin $value)")
  ;x máximo
  (set_tile "hz_xmax" drweixo_hz_xmax)
  (action_tile "hz_xmax" "(setq drweixo_hz_xmax $value)")
  ;x incremento
  (set_tile "hz_xgap" drweixo_hz_xgap)
  (action_tile "hz_xgap" "(setq drweixo_hz_xgap $value)")
  ;escala vertical
  (start_list "vt_scale")
  (mapcar 'add_list reg_scale_list)
  (end_list)
  (set_tile "vt_scale" drweixo_vt_scal)
  (action_tile "vt_scale" "(setq drweixo_vt_scal $value)")
  ;y mínimo
  (set_tile "vt_ymin" drweixo_vt_ymin)
  (action_tile "vt_ymin" "(setq drweixo_vt_ymin $value)")
  ;y máximo
  (set_tile "vt_ymax" drweixo_vt_ymax)
  (action_tile "vt_ymax" "(setq drweixo_vt_ymax $value)")
  ;y incremento
  (set_tile "vt_ygap" drweixo_vt_ygap)
  (action_tile "vt_ygap" "(setq drweixo_vt_ygap $value)")
  ;ações
  (action_tile "cancel" "(done_dialog 0)")
  (action_tile "accept" "(done_dialog 1)")
  (setq graf_dcl (start_dialog))
  (unload_dialog dcl_id)
  (if (= graf_dcl 1)
    (progn
      (command "undo" "m")
      (drweixo_write_file)
      (drweixo_draw)
    )
  )
  (princ)
)

(defun drweixo_draw ()
  (guarda '("blipmode" "cecolor" "celtype" "clayer" "cmdecho" "orthomode"
          "textstyle" "luprec" "osmode" ))
  (setq pt0 (getpoint "\nMarque a origem do eixo...")
	pt0_x (nth 0 pt0)
	pt0_y (nth 1 pt0)
  )
  (cn7_verylayer "Gráficos" 3)
  ;fator de correção e quantidades de grade
  (setq vt_factor (/ (distof drweixo_hz_scal) (distof (nth (fix (distof drweixo_vt_scal)) reg_scale_list)))
	hz_quant (fix (/ (- (distof drweixo_hz_xmax) (distof drweixo_hz_xmin)) (distof drweixo_hz_xgap)))
	vt_quant (fix (/ (- (distof drweixo_vt_ymax) (distof drweixo_vt_ymin)) (distof drweixo_vt_ygap)))
  )
  ;decimais dos textos
  (if (= 0 (- (distof drweixo_hz_xgap) (fix (distof drweixo_hz_xgap))))
    (setq graf_hz_txdec 0)
    (progn
      (setq graf_hz_txdec (getint "\nNúmero de casas decimais na numeração do eixo horizontal...<ENTER = 1>... "))
      (if (= nil graf_hz_txdec) (setq graf_hz_txdec 1))
    )
  )
  (if (= 0 (- (distof drweixo_vt_ygap) (fix (distof drweixo_vt_ygap))))
    (setq graf_vt_txdec 0)
    (progn
      (setq graf_vt_txdec (getint "\nNúmero de casas decimais na numeração do eixo vertical...<ENTER = 1>... "))
      (if (= nil graf_vt_txdec) (setq graf_vt_txdec 1))
    )
  )
  ;linetype da grade
  (setq grf_grdlty (list "Continuous" "hidden" "hidden2")
	grid_ltype (nth (fix (distof graf_glt)) grf_grdlty)
  )
  ;eixo horizontal
  (setq hz_pt_final (polar pt0 0 (- (distof drweixo_hz_xmax) (distof drweixo_hz_xmin)))
	hz_text (distof drweixo_hz_xmin)
  )
  (setvar "cecolor" graf_grd)
  (command "._line" "_non" pt0 "_non" hz_pt_final "")
  (command "._chprop" (entlast) "" "_p" "_lt" grid_ltype ""
	   "._array"  (entlast) "" "r" (1+ vt_quant) "1" (* vt_factor (distof drweixo_vt_ygap))
	   "._chprop" "_p" "" "_p" "_c" graf_eix "_lt" "bylayer" ""
  )
  (setq px pt0
	hz_text (distof drweixo_hz_xmin)
	px_text (polar px (/ (* 3 pi) 2) (*  0.3 cn7_blkscl))
  )
  (setvar "cecolor" graf_tik)
  (command "._line" "_non" px "_non" (polar px (/ (* 3 pi) 2) (*  0.2 cn7_blkscl)) "")
  (setvar "cecolor" graf_txc)
  (command "._text" "_s" cn7_txtsty "_tc" "_non" px_text cn7_txth 0 (rtos hz_text 2 graf_hz_txdec))
  (repeat hz_quant
    (setq px (polar px 0 (distof drweixo_hz_xgap))
	  px_text (polar px (/ (* 3 pi) 2) (*  0.3 cn7_blkscl))
	  hz_text (+ hz_text (distof drweixo_hz_xgap))
    )
    (setvar "cecolor" graf_tik)
    (command "._line" "_non" px "_non" (polar px (/ (* 3 pi) 2) (*  0.2 cn7_blkscl)) "")
    (setvar "cecolor" graf_txc)
    (command "._text" "_s" cn7_txtsty "_tc" "_non" px_text cn7_txth 0 (rtos hz_text 2 graf_hz_txdec) )
  )
  ;eixo vertical
  (setq vt_pt_final (polar pt0 (/ pi 2) (* vt_factor (- (distof drweixo_vt_ymax) (distof drweixo_vt_ymin))))
	vt_text (distof drweixo_vt_ymin)
  )
  (setvar "cecolor" graf_grd)
  (command "._line" "_non" pt0 "_non" vt_pt_final "")
  (command "._chprop" (entlast) "" "_p" "_lt" grid_ltype ""
	   "._array"  (entlast) "" "r" "1" (1+ hz_quant) (distof drweixo_hz_xgap)
	   "._chprop" "_p" "" "_p" "_c" graf_eix ""
  )
  (setq py pt0
	vt_text (distof drweixo_vt_ymin)
	py_text (polar py pi (*  0.3 cn7_blkscl))
  )
  (setvar "cecolor" graf_tik)
  (command "._line" "_non" py "_non" (polar py pi (*  0.2 cn7_blkscl)) "")
  (setvar "cecolor" graf_txc)
  (command "._text" "_s" cn7_txtsty "_mr" "_non" py_text cn7_txth 0 (rtos vt_text 2 graf_vt_txdec))
  (repeat vt_quant
    (setq py (polar py (/ pi 2) (* vt_factor (distof drweixo_vt_ygap)))
	  py_text (polar py pi (*  0.3 cn7_blkscl))
	  vt_text (+ vt_text (distof drweixo_vt_ygap))
    )
    (setvar "cecolor" graf_tik)
    (command "._line" "_non" py "_non" (polar py pi (*  0.2 cn7_blkscl)) "")
    (setvar "cecolor" graf_txc)
    (command "._text" "_s" cn7_txtsty "_mr" "_non" py_text cn7_txth 0 (rtos vt_text 2 graf_vt_txdec))
  )
  (command "._insert" (strcat cnp_root "/blocos/graf_capt") "_s" cn7_blkscl "_non" pt0 0
	   drweixo_hz_scal drweixo_hz_xmin drweixo_hz_xmax drweixo_hz_xgap
	   drweixo_vt_scal drweixo_vt_ymin drweixo_vt_ymax drweixo_vt_ygap
  )
  (devolve)
)


;escreve o arquivo de dados
(defun drweixo_write_file ()
  (setq file (open (strcat cnp_root "/config/grafdefault.txt") "w" "utf8"))
  (write-line drweixo_hz_xmin file)
  (write-line drweixo_hz_xmax file)
  (write-line drweixo_hz_xgap file)
  (write-line drweixo_vt_scal file)
  (write-line drweixo_vt_ymin file)
  (write-line drweixo_vt_ymax file)
  (write-line drweixo_vt_ygap file)
  (close file)
)

;lê os dados iniciais da DCL no arquivo de dados
(defun drweixo_file ()
  (if (findfile (strcat cnp_root "/config/grafdefault.txt"))
    (drweixo_readfile)
    (progn
      (setq file (open (strcat cnp_root "/config/grafdefault.txt") "w" "utf8"))
      (write-line "0" file)
      (write-line "30" file)
      (write-line "5" file)
      (write-line "50" file)
      (write-line "0" file)
      (write-line "30" file)
      (write-line "5" file)
      (close file)
      (drweixo_readfile)
    )
  )
)

;função que lê o arquivo de dados
(defun drweixo_readfile ()
  (setq	file (open (strcat cnp_root "/config/grafdefault.txt") "r" "utf8"))
  (setq	drweixo_hz_xmin (read-line file))
  (setq	drweixo_hz_xmax (read-line file))
  (setq	drweixo_hz_xgap (read-line file))
  (setq	drweixo_vt_scal (read-line file))
  (setq	drweixo_vt_ymin (read-line file))
  (setq	drweixo_vt_ymax (read-line file))
  (setq	drweixo_vt_ygap (read-line file))
  (close file)
)


;******************************************************************************
; Desenhadores de Gráficos ****************************************************
;******************************************************************************
(defun c:grg ()
  (if (/= cn7_dwgunit 1.0)
    (progn
      (cn7_alert_ok
	  "Por enquanto, os gráficos aplicam-se"
	  "apenas para desenhos em metros!"
	  "Aguardem novas atualizações..."
      )
      (exit)
     )
  )
  (drwgraf_file)
  (setq dcl_id (load_dialog (strcat cnp_root "/lisp/cadnorma.dcl")))
  (if (not (new_dialog "graf_draw" dcl_id)) (exit))
  (set_tile "drwgraf_radio" drwgraf_what)
  (if (= drwgraf_what "drwgraf_radio1")
    (set_tile "drwgraf_txt" "Cor dos Pontos:")
    (set_tile "drwgraf_txt" "Cor do Gráfico:")
  )
  (action_tile "drwgraf_radio" "(drwgraf_what_action)")
  (start_image "drwgraf_col")
  (fill_image  0  0
    (dimx_tile "drwgraf_col")
    (dimy_tile "drwgraf_col")
    (fix (distof drwgraf_color))
  )
  (end_image)
  (action_tile "drwgraf_col" "(drwgraf_grafcol)")
  (action_tile "cancel" "(done_dialog 0)")
  (action_tile "accept" "(done_dialog 1)")
  (setq gf_draw_dcl (start_dialog))
  (unload_dialog dcl_id)
  (if (= gf_draw_dcl 1)
    (progn
      (drwgraf_writefile)
      (setq vt_factor (/ (distof drweixo_hz_scal) (distof (nth (fix (distof drweixo_vt_scal)) reg_scale_list))))
      (if (= drwgraf_what "drwgraf_radio2")
	(gf_draw_pline)
	(gf_draw_point)
      )
    )
  )
  (princ)
)

;escolher cor do gráfico ou dos pontos
(defun drwgraf_grafcol ()
  (setq drwgraf_newcolor (acad_colordlg (fix (distof drwgraf_color))))
  (if (/= nil drwgraf_newcolor) (setq drwgraf_color (rtos drwgraf_newcolor 2 0)))
  (start_image "drwgraf_col")
  (fill_image  0  0
    (dimx_tile "drwgraf_col")
    (dimy_tile "drwgraf_col")
    (fix (distof drwgraf_color))
  )
  (end_image)
)

;ação ao selecionar o que fazer
(defun drwgraf_what_action ()
  (setq drwgraf_what $value)
  (if (= drwgraf_what "drwgraf_radio1")
    (set_tile "drwgraf_txt" "Cor dos Pontos:")
    (set_tile "drwgraf_txt" "Cor do Gráfico:")
  )
)

;lê os dados iniciais da DCL no arquivo de dados
(defun drwgraf_file ()
  (if (findfile (strcat cnp_root "/config/grafcolor.txt"))
    (drwgraf_readfile)
    (progn
      (setq file (open (strcat cnp_root "/config/grafcolor.txt") "w" "utf8"))
      (write-line "drwgraf_radio2" file)
      (write-line "6" file)
      (close file)
      (drwgraf_readfile)
    )
  )
)

;função que lê o arquivo de dados
(defun drwgraf_readfile ()
  (setq	file (open (strcat cnp_root "/config/grafcolor.txt") "r" "utf8"))
  (setq	drwgraf_what (read-line file))
  (setq	drwgraf_color (read-line file))
  (close file)
)

(defun drwgraf_writefile ()
  (setq file (open (strcat cnp_root "/config/grafcolor.txt") "w" "utf8"))
  (write-line drwgraf_what file)
  (write-line drwgraf_color file)
  (close file)
)

;************* desenha pline ***********************
(defun gf_draw_pline ()
  (guarda '("blipmode" "cecolor" "celtype" "clayer" "cmdecho" "orthomode"
          "textstyle" "luprec" "osmode" ))
  (cn7_verylayer "Gráficos" 3)
  (setq arq1 (getfiled "Selecione o Arquivo de Dados" (getvar "dwgprefix") "csv;txt;prn" 16))
  (setq arq  (open arq1 "r" "utf8"))
  (setq cont 0)
  (while (/= (read-line arq) nil)
    (setq cont (1+ cont))
  )
  (close arq)
  (command "pline")
  (setq arq  (open arq1 "r" "utf8"))
  (setvar "cecolor" drwgraf_color)
  (repeat cont
    (cn7_read_data)
    (gf_pline_draw)
  );repeat
  (close arq)
  (command "")
  (devolve)
  (princ)
)

(defun gf_pline_draw ()
  (setq x_pto2 (- (+ pt0_x (distof cn7_dado1)) (distof drweixo_hz_xmin))
	y_pto2 (+ pt0_y (* (- (distof cn7_dado2) (distof drweixo_hz_xmin)) vt_factor))
	pto_01 (list x_pto2 y_pto2)
  )
  (command "_non" pto_01)
)


;************* desenha points ***********************
(defun gf_draw_point ()
  (guarda '("blipmode" "cecolor" "celtype" "clayer" "cmdecho" "orthomode"
          "textstyle" "luprec" "osmode" ))
  (cn7_verylayer "Gráficos" 3)
  (setq arq1 (getfiled "Selecione o Arquivo de Dados" (getvar "dwgprefix") "csv;txt;prn" 8))
  (setq arq  (open arq1 "r" "utf8"))
  (setq cont 0)
  (while (/= (read-line arq) nil)
    (setq cont (1+ cont))
  )
  (close arq)
  (setq arq  (open arq1 "r" "utf8"))
  (setvar "cecolor" drwgraf_color)
  (repeat cont
    (cn7_read_data)
    (gf_point_draw)
  );repeat
  (close arq)
  (devolve)
  (princ)
)

(defun gf_point_draw ()
  (setq x_pto2 (- (+ pt0_x (distof cn7_dado1)) (distof drweixo_hz_xmin))
	y_pto2 (+ pt0_y (* (- (distof cn7_dado2) (distof drweixo_hz_xmin)) vt_factor))
	pto_01 (list x_pto2 y_pto2)
  )
  (command "point" "non" pto_01)
)


;******************************************************************************
; Rotina para extrair tabela de pontos    *************************************
;******************************************************************************
(defun c:grx ()
  (if (/= cn7_dwgunit 1.0)
    (progn
      (cn7_alert_ok
	  "Por enquanto, os gráficos aplicam-se"
	  "apenas para desenhos em metros!"
	  "Aguardem novas atualizações..."
      )
      (exit)
     )
  )
  (guarda '("blipmode" "cecolor" "celtype" "clayer" "cmdecho" "orthomode"
          "textstyle" "luprec" "osmode" ))
  (setq grp_type "2")
  (cn7_find_blkscl)
  (setq x0 0 y0 0)
  (setq
    pt0g (getpoint "\nMarque o ponto superior direito da tabela...")
    p0g1 (polar pt0g 0 (* cn7_blkscl 0.15))
    p0g (polar p0g1 (/ (* 3 pi) 2) (* cn7_blkscl 0.5))
    graf_counter 1
  )
  (command "._insert" (strcat cnp_root "/blocos/graf_tab") "_s" cn7_blkscl "_non" pt0g 0 "explode" (entlast) "")
  (while (/= nil (setq pto_atual (getpoint "\nMarque o ponto a identificar...")))
    (setq xa (nth 0 pto_atual)
	  ya (nth 1 pto_atual)
	  xra (rtos (+ (distof drweixo_hz_xmin) (- xa pt0_x)) 2 2)
	  yra (rtos (+ (distof drweixo_vt_ymin) (/ (- ya pt0_y) vt_factor)) 2 2)
    )
    (setq pt1 (polar p0g 0 (* cn7_blkscl 0.05))
	  p_txt1 (polar pt1 (/ (* 3 pi) 2) (* cn7_blkscl 0.41))
	  pt2 (polar p0g 0 (* cn7_blkscl 2.65))
	  p_txt2 (polar pt2 (/ (* 3 pi) 2) (* cn7_blkscl 0.41))
    )
    (setvar "cecolor" "2")
    (setq psimb_txt p_txt1)
    (cn7_txsimb "r80" "bl" xra 2 "Gráficos" "0")
    (setq psimb_txt p_txt2)
    (cn7_txsimb "r80" "br" yra 2 "Gráficos" "0")
    (setq p0g (polar p0g (/ (* 3 pi) 2) (* cn7_blkscl 0.5)))
    (setq graf_counter (1+ graf_counter))
    (if (= graf_counter 12)
      (progn
	(setq
	  p0g1 (polar p0g1 0 (* cn7_blkscl 3.8))
	  p0g (polar p0g1 (/ (* 3 pi) 2) (* cn7_blkscl 0.5))
	  graf_counter 1
	  )
	(command "._insert" (strcat cnp_root "/blocos/graf_tab") "non" p0g1 cn7_blkscl "" "" "explode" (entlast) "")
	);progn
      );if
    );while
  (devolve)
  (princ)
);defun


;******************************************************************************
;Rotina para extrair dados de um gráfico já desenhado    **********************
;******************************************************************************
(defun c:grc ()
  (if (/= cn7_dwgunit 1.0)
    (progn
      (cn7_alert_ok
	  "Por enquanto, os gráficos aplicam-se"
	  "apenas para desenhos em metros!"
	  "Aguardem novas atualizações..."
      )
      (exit)
     )
  )
  (setq dcl_id (load_dialog (strcat cnp_root "/lisp/cadnorma.dcl")))
  (if (not (new_dialog "graf_capt" dcl_id)) (exit))
  (action_tile "cancel" "(done_dialog 0)")
  (action_tile "accept" "(done_dialog 1)")
  (setq x (dimx_tile "graf_capt")
        y (dimy_tile "graf_capt"))
  (start_image "graf_capt")
  (slide_image 0 0 x y (strcat cnp_root "/slides/graf_capt"))
  (end_image)
  (setq graf_dcl (start_dialog))
  (unload_dialog dcl_id)
  (if (= graf_dcl 1) (graf_capture))
  (princ)
);defun


(defun graf_capture ()
  (prompt "\nSelecione o traço oblíquo na origem dos eixos do gráfico a identificar...")
  (setq ent1 (car (entsel)))
  (if (and
	(= (strcase (cdr (assoc 0 (entget ent1)))) "INSERT")
	(= (strcase (cdr (assoc 2 (entget ent1)))) "GRAF_CAPT")
      );and
    (progn
      (graf_extract_data)
      (setq vt_factor (/ (distof drweixo_hz_scal) (distof (nth (fix (distof drweixo_vt_scal)) reg_scale_list))))
      (prompt "\nDados Extraídos com sucesso! Agora você já pode operar neste gráfico.")
    )
    (progn
      (alert "\nO objeto selecionado não contém os dados requeridos...")
      (quit)
    );progn case F
  );if
);defun


(defun graf_extract_data ()
  (setq pto_inicial (cdr (assoc 10 (entget ent1)))
	gf_x0 (nth 0 pto_inicial)
	gf_y0 (nth 1 pto_inicial)
	pt0_x gf_x0
	pt0_y gf_y0
  )
;;;  (while (/= nil (setq ent1 (entnext ent1)))
  (while (/= "SEQEND" (strcase (cdr (assoc 0 (entget (setq ent1 (entnext ent1)))))) )
    (if
      (= "ATTRIB" (strcase (cdr (assoc 0 (entget ent1)))))
      (graf_extract_cond)
    )
  )
)

(defun graf_extract_cond ()
  (cond
    ((= "HZ_SCALE" (strcase (cdr (assoc 2 (entget ent1)))))
     (setq drweixo_hz_scal (cdr (assoc 1 (entget ent1))))
    )
    ((= "HZ_XMIN" (strcase (cdr (assoc 2 (entget ent1)))))
     (setq drweixo_hz_xmin (cdr (assoc 1 (entget ent1))))
    )
    ((= "HZ_XMAX" (strcase (cdr (assoc 2 (entget ent1)))))
     (setq drweixo_hz_xmax (cdr (assoc 1 (entget ent1))))
    )
    ((= "HZ_GAP" (strcase (cdr (assoc 2 (entget ent1)))))
     (setq drweixo_hz_xgap (cdr (assoc 1 (entget ent1))))
    )
    ((= "VT_SCALE" (strcase (cdr (assoc 2 (entget ent1)))))
     (setq drweixo_vt_scal (cdr (assoc 1 (entget ent1))))
    )
    ((= "VT_YMIN" (strcase (cdr (assoc 2 (entget ent1)))))
     (setq drweixo_vt_ymin (cdr (assoc 1 (entget ent1))))
    )
    ((= "VT_YMAX" (strcase (cdr (assoc 2 (entget ent1)))))
     (setq drweixo_vt_ymax (cdr (assoc 1 (entget ent1))))
    )
    ((= "VT_GAP" (strcase (cdr (assoc 2 (entget ent1)))))
     (setq drweixo_vt_ygap (cdr (assoc 1 (entget ent1))))
    )
  )
)




;Define fator de correção para áreas **********************************
(defun aa_fator ()
  (setq area_fator (getreal "\nEntre com o fator de multiplicação para as áreas..."))
  (if (= nil area_fator) (setq area_fator 1))
)


;Escreve a área medida com fator de correção **********************************
(defun c:ea_fator () (ea_fact) (princ))

(defun ea_fact ()
  	(setq laymo (getvar "clayer"))
  	(if (= nil area_fator) (aa_fator))
	(area_verify)
  	(if (= "SIM" (strcase area_m2))
	  (setq area_text (strcat (rtos (* (getvar "AREA") area_fator) 2 area_dec) " m2"))
	  (setq area_text (rtos (* (getvar "AREA") area_fator) 2 area_dec))
	)
	(setq p1 (getpoint "\n Escolha o ponto central do texto... "))
	(command "._layer" "_m" area_layer "" "._text" "_s" area_style "_c" "_non" p1 0 area_text "._chprop" "._last" "" "_c" area_color "")
	(setvar "clayer" laymo)
)

;\transcreve a área medida com fator de correção **********************************
(defun c:ta_fator ()
  	(setq laymo (getvar "clayer"))
  	(if (= nil area_fator) (aa_fator))
	(area_verify)
        (if (= "SIM" (strcase area_m2))
    		(setq new (cons 1 (strcat (rtos (* (getvar "area") area_fator) 2 area_dec) " m2")))
      		(setq new (cons 1 (rtos (* (getvar "area") area_fator) 2 area_dec)))
    	)
    	(prompt "\nSelecione o texto a ser modificado...")
    	(setq ent2 (entget (car (entsel))))
    	(entmod (subst new (assoc 1 ent2) ent2))
  (princ)
)



;Mede a última polilinha e escreve sua área *************************
(defun c:el_fator ()
  (if (and (/= "LWPOLYLINE" (cdr (assoc 0 (setq last_ent (entget (entlast))))))
	   (/= "POLYLINE" (cdr (assoc 0 (setq last_ent (entget (entlast))))))
      );and
    (progn
      	(alert "A última entidade não é uma polyline...")
      	(exit)
    )
    (progn
	(command "area" "o" (entlast))
        (ea_fact)
    )
  );if
  (princ)
);defun



;Idem Anterior - Mede a última polilinha e escreve sua área *************************
(defun c:arl ()
  (if (and (/= "LWPOLYLINE" (cdr (assoc 0 (setq last_ent (entget (entlast))))))
	   (/= "POLYLINE" (cdr (assoc 0 (setq last_ent (entget (entlast))))))
      );and
    (progn
      	(alert "A última entidade não é uma polyline...")
      	(exit)
    )
    (progn
	(command "area" "o" (entlast))
        (ea_fact)
    )
  );if
  (princ)
);defun



;cnp_34

;******************************************************************************
;******************************************************************************
;NOTAS GERAIS <NOG>************************************************************
;******************************************************************************
;******************************************************************************
(defun c:nog ()
  (guarda '("blipmode" "cecolor" "celtype" "clayer" "cmdecho" "orthomode"
          "textstyle" "luprec" "osmode" ))
  (nog_main)
  (devolve)
  (princ)
)

;comando principal
(defun nog_main ()
  (setq nog_backey 0)
  (setq grp_type "2")
  (cn7_find_blkscl)
  (nog_cfg_file)
  (nog_deftexts)
  (initget 128)
  (setq pt1 (getpoint "\nContinuar/<Clique no Ponto Inicial...>:"))
  (cond
      ((= 'LIST (type pt1))
       (nog_action)
      )
      ((= 'STR  (type pt1))
       (cond
	 ((= "C" (strcase pt1))
	  (prompt "\nSelecione o último texto para prosseguir...")
	  (setq nog_sel (entsel)
		nog_sel_point (cdr (assoc 10 (entget (car nog_sel))))
		pt1 (polar nog_sel_point (/ (* 3 pi) 2) (* nog_notas_heigth 3.2))
	  )
	  (cn7_verylayer "Notas" (fix (distof nogcfg_notcol)))
	  (nog_action)
	 )
	 (t
	  (alert "\nOpção inválida!\nDigite 'F' para Formatar,\n'C' para Continuar ou\nMarque o primeiro ponto (Título)...")
	  (nog_main)
	 )
       )
     )
   )
)

;insere o título
(defun nog_instit ()
  (nog_save_file)
  (nog_read_file)
  (nog_deftexts)
  (setq colmo (getvar "cecolor"))
  (setvar "cecolor" nogcfg_titcol)
  (cn7_verylayer "Notas" (fix (distof nogcfg_notcol)))
  (command "._text" "_s" nog_title_style "_non" pt1 nog_title_heigth "0" nogcfg_tittxt)
  (setvar "cecolor" colmo)
  (setq pt1 (polar pt1 (/ (* 3 pi) 2) (* nog_title_heigth 2.5)))
  (setq resp (getstring "\nPressione <ENTER> para continuar ou <ESC> para terminar... "))
  (if (or (= nil resp) (= "" resp))    
    (nog_action)
  )
)

;insere a nota atual
(defun nog_insert ()
  (nog_save_file)
  (nog_read_file)
  (nog_deftexts)
  (setq colmo (getvar "cecolor"))
  (setvar "cecolor" nogcfg_notcol)
  (if (/= "" nog_linha1)
    (progn
      (command "._text" "_s" nog_notas_style  "_non" pt1 nog_notas_heigth "0" nog_linha1)
      (setq pt1 (polar pt1 (/ (* 3 pi) 2) (* nog_notas_heigth 1.6)))
    )
  )
  (if (/= "" nog_linha2)
    (progn
      (command "._text" "_s" nog_notas_style  "_non" pt1 nog_notas_heigth "0" nog_linha2)
      (setq pt1 (polar pt1 (/ (* 3 pi) 2) (* nog_notas_heigth 1.6)))
    )
  )
  (if (/= "" nog_linha3)
    (progn
      (command "._text" "_s" nog_notas_style  "_non" pt1 nog_notas_heigth "0" nog_linha3)
      (setq pt1 (polar pt1 (/ (* 3 pi) 2) (* nog_notas_heigth 1.6)))
    )
  )
  (if (/= "" nog_linha4)
    (progn
      (command "._text" "_s" nog_notas_style  "_non" pt1 nog_notas_heigth "0" nog_linha4)
      (setq pt1 (polar pt1 (/ (* 3 pi) 2) (* nog_notas_heigth 1.6)))
    )
  )
  (if (/= "" nog_linha5)
    (progn
      (command "._text" "_s" nog_notas_style  "_non" pt1 nog_notas_heigth "0" nog_linha5)
      (setq pt1 (polar pt1 (/ (* 3 pi) 2) (* nog_notas_heigth 1.6)))
    )
  )
  (setq pt1 (polar pt1 (/ (* 3 pi) 2) (* nog_notas_heigth 1.6)))
  (setvar "cecolor" colmo)
  (devolve)
  (setq resp (getstring "\nPressione <ENTER> para continuar ou <ESC> para terminar... "))
  (if (or (= nil resp) (= "" resp))    
    (nog_action)
  )
)

;abre a dcl de controle e inserção de notas
(defun nog_action ()
  (setq dcl_id (load_dialog (strcat cnp_root "/lisp/cadnorma.dcl")))
  (if (not (new_dialog "nog" dcl_id)) (exit))
  ;lista da pop_list
  (setq nog_family_list (list"Geral" "Arquitetura" "Paisagismo" "Urbanismo" "Elétrica" "Telefone"
			"Rede Lógica" "Água" "Esgoto" "Incêndio" "Aterramento" "Ar Condicionado"
			"Concreto" "Metálica" "Gás" "Automação" "Alarme" "CFTV" "Som"
			"Topografia" "User_01" "User_02" "User_03")
  )
  (start_list "nog_pop")
  (mapcar 'add_list nog_family_list)
  (end_list)
  ;define o status dos botões
  (mode_tile "nog_prev" 1)
  (mode_tile "nog_next" 1)
  ;define a nota atual
  (if (= nil nog_family)
    (setq nog_family "0" nog_famcode "00")
  )
  (set_tile "nog_pop" nog_family)
  (nog_conta_notas)
  (nog_nextprev)
  ;define o arquivo atual, próximo e anterior
  (if (= nil nog_register) (setq nog_register "1"))
  (setq nog_file (strcat cnp_netroot "/notas/cnng" nog_famcode nog_register ".txt"))
  (nog_read_file)
  (nog_updlines)
  (set_tile "nog_current_note" nog_register)
  (action_tile "nog_pop" "(nog_pop_action)")
  (action_tile "nog_linha1" "(setq nog_linha1 $value)")
  (action_tile "nog_linha2" "(setq nog_linha2 $value)")
  (action_tile "nog_linha3" "(setq nog_linha3 $value)")
  (action_tile "nog_linha4" "(setq nog_linha4 $value)")
  (action_tile "nog_linha5" "(setq nog_linha5 $value)")
  (action_tile "nog_prev" "(nog_prev_action)")
  (action_tile "nog_next" "(nog_next_action)")
  (action_tile "nog_new" "(nog_new_action)")
  (action_tile "cancel" "(done_dialog 0)")
  (action_tile "accept" "(done_dialog 1)")
  (action_tile "nog_config" "(done_dialog 2)")
  (action_tile "nog_insert" "(done_dialog 3)")
  (action_tile "nog_tit" "(done_dialog 4)")
  (action_tile "nog_pick1" "(done_dialog 5)")
  (action_tile "nog_pick2" "(done_dialog 6)")
  (action_tile "nog_pick3" "(done_dialog 7)")
  (action_tile "nog_pick4" "(done_dialog 8)")
  (action_tile "nog_pick5" "(done_dialog 9)")
  (setq nog_dcl (start_dialog))
  (unload_dialog dcl_id)
  (if (= nog_dcl 1) (nog_ok))
  (if (= nog_dcl 2) (nog_cfg_action))
  (if (= nog_dcl 3) (nog_insert))
  (if (= nog_dcl 4) (nog_instit))
  (if (= nog_dcl 5) (nog_pick_action 1))
  (if (= nog_dcl 6) (nog_pick_action 2))
  (if (= nog_dcl 7) (nog_pick_action 3))
  (if (= nog_dcl 8) (nog_pick_action 4))
  (if (= nog_dcl 9) (nog_pick_action 5))
)

;captura o texto na tela
(defun nog_pick_action (ng_line)
  (prompt "\nSelecione um texto para copiar seu conteúdo...")
  (setq ent1 (car (entsel))
	ent1_type (cdr (assoc 0 (entget ent1)))
  )
  (if (/= "TEXT" ent1_type)
    (progn
      (alert "Seleção inválida!\nClique em um texto\npara copiar o conteúdo...")
      (nog_pick1_action)
    )
  )
  (cond
    ((= ng_line 1) (setq nog_linha1 (cdr (assoc 1 (entget ent1)))))
    ((= ng_line 2) (setq nog_linha2 (cdr (assoc 1 (entget ent1)))))
    ((= ng_line 3) (setq nog_linha3 (cdr (assoc 1 (entget ent1)))))
    ((= ng_line 4) (setq nog_linha4 (cdr (assoc 1 (entget ent1)))))
    ((= ng_line 5) (setq nog_linha5 (cdr (assoc 1 (entget ent1)))))
  )
  (nog_save_file)
  (nog_action)
)


;botão ok
(defun nog_ok ()
  (nog_save_file)
  (nog_read_file)
)

;define os estilos de textos para notas
(defun nog_deftexts ()
  (setq nog_stylist (list "r50" "r60" "r70" "r80" "r90" "r100" "r120" "r140" "r175" "r200"
			   "t1" "t2" "t3" "t4" "t5" "t6" "t7"))
  (setq cn7_txtsty (nth (fix (distof nogcfg_titsty)) nog_stylist))
  (cn7_text_hfinal)
  (cn7_text_height)
  (setq nog_title_style cn7_txtsty
	nog_title_heigth cn7_txth
  )
  (setq cn7_txtsty (nth (fix (distof nogcfg_notsty)) nog_stylist))
  (cn7_text_hfinal)
  (cn7_text_height)
  (setq nog_notas_style cn7_txtsty
	nog_notas_heigth cn7_txth
  )
)


;configuração das notas
(defun nog_cfg_action ()
  (nog_cfg_file)
  (setq dcl_id (load_dialog (strcat cnp_root "/lisp/cadnorma.dcl")))
  (if (not (new_dialog "nog_config" dcl_id)) (exit))
  ;layer das notas gerais
  (set_tile "nog_cfg_alllay" nogcfg_alllay)
  ;título
  (set_tile "nog_cfg_tittxt" nogcfg_tittxt)
  (action_tile "nog_cfg_tittxt" "(setq nogcfg_tittxt $value)")
  ;estilo do título
  (setq nog_stylist (list "r50" "r60" "r70" "r80" "r90" "r100" "r120" "r140" "r175" "r200"
			   "t1" "t2" "t3" "t4" "t5" "t6" "t7"))
  (start_list "nog_cfg_titsty")
  (mapcar 'add_list nog_stylist)
  (end_list)
  (set_tile "nog_cfg_titsty" nogcfg_titsty)
  (action_tile "nog_cfg_titsty" "(setq nogcfg_titsty $value)")
  ;cor do título
  (start_image "nog_cfg_titcol")
  (fill_image  0  0
    (dimx_tile "nog_cfg_titcol")
    (dimy_tile "nog_cfg_titcol")
    (fix (distof nogcfg_titcol))
  )
  (end_image)
  (action_tile "nog_cfg_titcol" "(nogcfg_titcol_action)")
  ;estilo das notas
  (setq nog_stylist (list "r50" "r60" "r70" "r80" "r90" "r100" "r120" "r140" "r175" "r200"
			  "t1" "t2" "t3" "t4" "t5" "t6" "t7"))
  (start_list "nog_cfg_notsty")
  (mapcar 'add_list nog_stylist)
  (end_list)
  (set_tile "nog_cfg_notsty" nogcfg_notsty)
  (action_tile "nog_cfg_notsty" "(setq nogcfg_notsty $value)")
  ;cor das notas
  (start_image "nog_cfg_notcol")
  (fill_image  0  0
    (dimx_tile "nog_cfg_notcol")
    (dimy_tile "nog_cfg_notcol")
    (fix (distof nogcfg_notcol))
  )
  (end_image)
  (action_tile "nog_cfg_notcol" "(nogcfg_notcol_action)")
  ;ações dos botões ok_cancel
  (action_tile "cancel" "(done_dialog 0)")
  (action_tile "accept" "(done_dialog 1)")
  (setq nog_cfg_dcl (start_dialog))
  (unload_dialog dcl_id)
  (if (= 1 nog_cfg_dcl)
    (progn
      (nog_cfg_writefile)
      (if (= nog_backey 1)
	(nog_main)
	(nog_action)
      )
    )
  )
)

;escolher cor do título
(defun nogcfg_notcol_action ()
  (setq nogcfg_newnotcol (acad_colordlg (fix (distof nogcfg_notcol))))
  (if (/= nil nogcfg_newnotcol) (setq nogcfg_notcol (rtos nogcfg_newnotcol 2 0)))
  (start_image "nog_cfg_notcol")
  (fill_image  0  0
    (dimx_tile "nog_cfg_notcol")
    (dimy_tile "nog_cfg_notcol")
    (fix (distof nogcfg_notcol))
  )
  (end_image)
)

;escolher cor do título
(defun nogcfg_titcol_action ()
  (setq nogcfg_newtitcol (acad_colordlg (fix (distof nogcfg_titcol))))
  (if (/= nil nogcfg_newtitcol) (setq nogcfg_titcol (rtos nogcfg_newtitcol 2 0)))
  (start_image "nog_cfg_titcol")
  (fill_image  0  0
    (dimx_tile "nog_cfg_titcol")
    (dimy_tile "nog_cfg_titcol")
    (fix (distof nogcfg_titcol))
  )
  (end_image)
)


;arquivo de configurações das notas
(defun nog_cfg_file ()
  (if (findfile (strcat cnp_root "/config/nog_cfgn.txt"))
    (nog_cfg_readfile)
    (progn
      (setq file (open (strcat cnp_netroot "/config/nog_cfgn.txt") "w" "utf8"))
      (write-line "Notas_gerais" file)
      (write-line "NOTAS GERAIS" file)
      (write-line "7" file)
      (write-line "6" file)
      (write-line "5" file)
      (write-line "3" file)
      (close file)
      (nog_cfg_readfile)
    )
  )
)


;escreve o arquivo de dados
(defun nog_cfg_writefile ()
  (setq file (open (strcat cnp_root "/config/nog_cfgn.txt") "w" "utf8"))
  (write-line nogcfg_alllay file)
  (write-line nogcfg_tittxt file)
  (write-line nogcfg_titsty file)
  (write-line nogcfg_titcol file)
  (write-line nogcfg_notsty file)
  (write-line nogcfg_notcol file)
  (close file)
)


;função que lê o arquivo de dados
(defun nog_cfg_readfile ()
  (setq	file (open (strcat cnp_root "/config/nog_cfgn.txt") "r" "utf8"))
  (setq	nogcfg_alllay (read-line file))
  (setq	nogcfg_tittxt (read-line file))
  (setq	nogcfg_titsty (read-line file))
  (setq	nogcfg_titcol (read-line file))
  (setq	nogcfg_notsty (read-line file))
  (setq	nogcfg_notcol (read-line file))
  (close file)
)

;botão 'Nova' - cria mais uma nota
(defun nog_new_action ()
  (setq nog_register (rtos (+ 1 (distof nog_totnotes)) 2 0)
	nog_linha1 (strcat "NOTA " nog_register)
	nog_linha2 ""
	nog_linha3 ""
	nog_linha4 ""
	nog_linha5 ""
  )
  (setq nog_file (strcat cnp_netroot "/notas/cnng" nog_famcode nog_register ".txt"))
  (nog_save_file)
  (nog_conta_notas)
  (nog_read_file)
  (nog_updlines)
  (set_tile "nog_current_note" nog_register)
  (nog_nextprev)
)


;verifica se é o último ou ou primeiro registro
(defun nog_nextprev ()
  (if (= "1" nog_register)
    (mode_tile "nog_prev" 1)
    (mode_tile "nog_prev" 0)
  )
  (if (= nog_totnotes nog_register)
    (mode_tile "nog_next" 1)
    (mode_tile "nog_next" 0)
  )
)

;ação do botão 'Próxima'
(defun nog_next_action ()
  (nog_save_file)
  (setq nog_register (rtos (+ 1 (distof nog_register)) 2 0))
  (setq nog_file (strcat cnp_netroot "/notas/cnng" nog_famcode nog_register ".txt"))
  (nog_read_file)
  (nog_updlines)
  (set_tile "nog_current_note" nog_register)
  (nog_nextprev)
)

;ação do botão 'Anterior'
(defun nog_prev_action ()
  (nog_save_file)
  (setq nog_register (rtos (- (distof nog_register) 1) 2 0))
  (setq nog_file (strcat cnp_netroot "/notas/cnng" nog_famcode nog_register ".txt"))
  (nog_read_file)
  (nog_updlines)
  (set_tile "nog_current_note" nog_register)
  (nog_nextprev)
)


;conta a quantidade de notas existentes para a família selecionada
(defun nog_conta_notas ()
  (setq counter 1)
  (while (findfile (strcat cnp_netroot "/notas/cnng" nog_famcode (rtos counter 2 0) ".txt"))
    (setq counter (1+ counter))
  )
  (setq counter (1- counter)
	nog_totnotes (rtos counter 2 0)
  )
  (set_tile "nog_total_notes" (rtos counter 2 0))
)


;atualiza as linhas da nota atual
(defun nog_updlines ()
  (set_tile "nog_linha1" nog_linha1)
  (set_tile "nog_linha2" nog_linha2)
  (set_tile "nog_linha3" nog_linha3)
  (set_tile "nog_linha4" nog_linha4)
  (set_tile "nog_linha5" nog_linha5)
)


;grava o arquivo de notas atual
(defun nog_save_file ()
  (setq open_nog_file (open nog_file "w" "utf8"))
  (write-line nog_linha1 open_nog_file)
  (write-line nog_linha2 open_nog_file)
  (write-line nog_linha3 open_nog_file)
  (write-line nog_linha4 open_nog_file)
  (write-line nog_linha5 open_nog_file)
  (close open_nog_file)
)

;lê o arquivo de notas atual
(defun nog_read_file ()
  (if (findfile nog_file)
    (setq open_nog_file (open nog_file "r" "utf8")
	  nog_linha1 (read-line open_nog_file)
	  nog_linha2 (read-line open_nog_file)
	  nog_linha3 (read-line open_nog_file)
	  nog_linha4 (read-line open_nog_file)
	  nog_linha5 (read-line open_nog_file)
    )
    (close open_nog_file)
  )
)

;define o código da família
(defun nog_pop_action ()
  (nog_save_file)
  (setq nog_family $value)
  (setq nog_register "1")
  (if (= 1 (strlen nog_family))
    (setq nog_famcode (strcat "0" nog_family))
    (setq nog_famcode nog_family)
  )
  (setq nog_file (strcat cnp_netroot "/notas/cnng" nog_famcode nog_register ".txt"))
  (nog_read_file)
  (nog_updlines)
  (nog_conta_notas)
  (nog_nextprev)
  (set_tile "nog_current_note" nog_register)
)


;inicialização do QuantNorma
(cnqt_start_readfile)
(princ)

;cnp_50

(defun c:nv ()
  (setq s1 (ssget))
  (setq elev (getreal "\nNível para os elementos selecionados..."))
  (command "change" s1 "" "p" "e" elev "")
  (princ)
)

;Load External Lisp
(load (strcat cnp_root "/lisp/chtext"))
(load (strcat cnp_root "/lisp/aexplode"))
(load (strcat cnp_root "/lisp/flatten"))
(load (strcat cnp_root "/lisp/ll-tt-xx"))
(load (strcat cnp_root "/lisp/tremer"))
(load (strcat cnp_root "/lisp/ssx"))
  
(princ)
