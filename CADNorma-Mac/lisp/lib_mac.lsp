; Biblioteca Mac por seleção de DWG; usa metadados originais de grupo.
(defun c:lib (/ picked name meta f)
  (setq picked (getfiled "CADNorma: selecione um bloco DWG" (strcat cnp_root "/blocos/") "dwg" 0))
  (if picked
    (progn
      (setq name (strcase (vl-filename-base picked) T))
      (if (/= (strlen name) 14)
        (alert "Nome de bloco CADNorma invalido; selecione um arquivo da biblioteca.")
        (progn
          (setq lib_blkpfx (substr name 1 4) lib_blkfam (substr name 5 2)
                lib_blkgrp (substr name 7 2) lib_blksub (substr name 9 2)
                lib_blkpag (substr name 11 2) lib_blkblk (substr name 13 2)
                lib_currdwg picked lib_inslay "0" lib_blktog "0" lib_blkscl "1.0")
          (setq meta (strcat cnp_root "/slides/" (substr name 1 10) ".sgp"))
          (if (not (findfile meta))
            (alert (strcat "Metadados do grupo nao encontrados: " meta))
            (progn
              (setq f (open meta "r" "utf8"))
              (setq grp_type (read-line f) grp_unit (read-line f)
                    lib_currsgp_layname (read-line f) lib_currsgp_laycol (read-line f))
              (close f)
              (if (and grp_type grp_unit (distof grp_unit) (> (distof grp_unit) 0.0) lib_currsgp_layname lib_currsgp_laycol (distof lib_currsgp_laycol))
                (if (and cn7_dwgunit (> cn7_dwgunit 0.0) (or (= grp_type "1") (and cn7_msscl (> cn7_msscl 0.0))))
                  (lib_lastlib_insert)
                  (alert "Configure as unidades e a escala do desenho com CFG antes de inserir blocos."))
                (alert "Metadados incompletos: insercao cancelada."))
            )
          )
        )
      )
    )
  )
  (princ)
)
(princ "\nLIB Mac: selecione um DWG pelo nome; miniaturas ainda indisponiveis.\n")
(princ)
