; Carregar apos carregar_cadnorma_mac.lsp e executar CNMACTESTE.
(defun cnp:test-record (label ok detail)
  (write-line (strcat (if ok "PASS " "FAIL ") label " | " detail) cnp_test_log)
  (prompt (strcat "\n" (if ok "PASS " "FAIL ") label))
  (if (not ok) (setq cnp_test_fail (1+ cnp_test_fail)))
)
(defun c:cnmacteste (/ cnp_test_log cnp_test_fail n id src dst f val)
  (if (not cnp_root) (progn (alert "Carregue o adaptador primeiro.") (exit)))
  (setq cnp_test_fail 0 cnp_test_log (open (strcat cnp_root "/auditoria/teste-mac.txt") "w" "utf8"))
  (if (not cnp_test_log) (progn (alert "Falha ao abrir log de teste") (exit)))
  (write-line "CADNorma - smoke test executado pelo usuario" cnp_test_log)
  (write-line (strcat "ACADVER=" (getvar "ACADVER") " PLATFORM=" (getvar "PLATFORM") " LISPSYS=" (vl-princ-to-string (getvar "LISPSYS"))) cnp_test_log)
  (foreach n '("lisp/cadnorma.lsp" "modelos/cadnorma_água.dwg" "modelos/cadnorma_elétrica.dwg" "blocos/cadnorma_config.dwg" "slides/cadnorma.sld")
    (cnp:test-record n (findfile (strcat cnp_root "/" n)) "presenca do recurso"))
  (foreach n '("lisp/cadnorma.dcl" "lisp/cnmac.dcl" "lisp/gráficos.dcl")
    (setq id (load_dialog (strcat cnp_root "/" n)))
    (cnp:test-record n (> id 0) "load_dialog; nao valida layout visual")
    (if (> id 0) (unload_dialog id)))
  (foreach n '("DIMLUNIT" "DIMSHO" "BLIPMODE" "REGENMODE")
    (cnp:test-record n (not (null (getvar n))) "variavel requerida pelo legado"))
  (setq src (strcat cnp_root "/auditoria/fixture-origem.txt") dst (strcat cnp_root "/auditoria/fixture-destino.txt"))
  (setq f (open src "w" "utf8")) (write-line "água elétrica ação" f) (close f)
  (setq f (open dst "w" "utf8")) (write-line "anterior" f) (close f)
  (cnp:copy-overwrite src dst)
  (setq f (open dst "r" "utf8") val (read-line f)) (close f)
  (cnp:test-record "copia com sobrescrita e UTF-8" (= val "água elétrica ação") "destino relido; backup anterior preservado na raiz")
  (reg_scale)
  (cnp:test-record "escalas CADNorma" (> (length reg_scale_list) 0) "reg_scale executada; lista nao vazia")
  (write-line (strcat "Falhas=" (itoa cnp_test_fail)) cnp_test_log)
  (close cnp_test_log)
  (prompt (strcat "\nLog: " cnp_root "/auditoria/teste-mac.txt. Este smoke test nao valida comandos de desenho nem equivalencia Windows."))
  (princ)
)
(princ "\nExecute CNMACTESTE depois de carregar o CADNorma Mac.")
(princ)
